// fk_gerber.ulp — Gerber/Excellon: имена JLCPCB, архив, разбор, SVG-превью, параметры платы
// dmxON FabKit · dmxON by AlexSmith 2026 · см. LICENSE.md

// ---------------------------------------------------------------- файлы CAM-выгрузки Fusion

int n_gf = 0;
string gf_src[], gf_code[], gf_name[], gf_dst[];
int gf_order[], gf_size[];

string gb_job = "";            // содержимое gerber_job.gbrjob

string lower(string s)
{
    return strlwr(s);
}

// номер слоя из имени copper_inner_l3.gbr -> 3
int name_layer_no(string fn)
{
    int p = strrstr(fn, "_l");
    if (p < 0) return 0;
    return strtol(strsub(fn, p + 2));
}

// name — подпись слоя на языке интерфейса
void gf_add(string src, string code, string name, int order)
{
    gf_src[n_gf] = src; gf_code[n_gf] = code; gf_name[n_gf] = name;
    gf_order[n_gf] = order; gf_dst[n_gf] = ""; gf_size[n_gf] = 0;
    n_gf++;
}

// разобрать список файлов выгрузки (dir /s /b) и назначить имена JLCPCB
void gerber_classify(string listfile)
{
    string lines[];
    n_gf = 0;
    gb_job = "";
    int n = fileread(lines, listfile);
    int inner_no[];
    string inner_src[];
    int n_in = 0, i, k;
    for (i = 0; i < n; i++) {
        string p = trim(replace_all(lines[i], "\\", "/"));
        if (p == "") continue;
        string fn = lower(filename(p));
        string ext = lower(fileext(p));
        if (ext == ".gbrjob") { fileread(gb_job, p); continue; }
        if (strstr(p, "/Assembly/") >= 0) continue;
        if (starts_with(fn, "copper_top")) gf_add(p, "GTL", L("Медь, верхний слой", "Top copper"), 10);
        else if (starts_with(fn, "copper_bottom")) gf_add(p, "GBL", L("Медь, нижний слой", "Bottom copper"), 90);
        else if (starts_with(fn, "copper_inner")) { inner_no[n_in] = name_layer_no(strsub(fn, 0, strlen(fn) - strlen(ext))); inner_src[n_in] = p; n_in++; }
        else if (starts_with(fn, "soldermask_top")) gf_add(p, "GTS", L("Паяльная маска, верх", "Top solder mask"), 5);
        else if (starts_with(fn, "soldermask_bottom")) gf_add(p, "GBS", L("Паяльная маска, низ", "Bottom solder mask"), 95);
        else if (starts_with(fn, "solderpaste_top")) gf_add(p, "GTP", L("Паста (трафарет), верх", "Top paste (stencil)"), 4);
        else if (starts_with(fn, "solderpaste_bottom")) gf_add(p, "GBP", L("Паста (трафарет), низ", "Bottom paste (stencil)"), 96);
        else if (starts_with(fn, "silkscreen_top")) gf_add(p, "GTO", L("Шелкография, верх", "Top silkscreen"), 3);
        else if (starts_with(fn, "silkscreen_bottom")) gf_add(p, "GBO", L("Шелкография, низ", "Bottom silkscreen"), 97);
        else if (starts_with(fn, "profile")) gf_add(p, "GKO", L("Контур платы", "Board outline"), 1);
        else if (ext == ".xln" || ext == ".drl" || ext == ".txt" && strstr(fn, "drill") >= 0) {
            string code = "XLN";
            for (k = 0; k < n_gf; k++) if (gf_code[k] == "XLN") code = "XLN" + istr(k);
            gf_add(p, code, L("Сверловка (металлизированные и нет)", "Drill (plated + non-plated)"), 99);
        }
        else {
            // уже в формате JLCPCB (задание CAM dmxON JLCPCB): слой — по расширению
            string e = strupr(strsub(ext, 1));
            if (e == "GTL") gf_add(p, e, L("Медь, верхний слой", "Top copper"), 10);
            else if (e == "GBL") gf_add(p, e, L("Медь, нижний слой", "Bottom copper"), 90);
            else if (e == "GTS") gf_add(p, e, L("Паяльная маска, верх", "Top solder mask"), 5);
            else if (e == "GBS") gf_add(p, e, L("Паяльная маска, низ", "Bottom solder mask"), 95);
            else if (e == "GTP") gf_add(p, e, L("Паста (трафарет), верх", "Top paste (stencil)"), 4);
            else if (e == "GBP") gf_add(p, e, L("Паста (трафарет), низ", "Bottom paste (stencil)"), 96);
            else if (e == "GTO") gf_add(p, e, L("Шелкография, верх", "Top silkscreen"), 3);
            else if (e == "GBO") gf_add(p, e, L("Шелкография, низ", "Bottom silkscreen"), 97);
            else if (e == "GKO") gf_add(p, e, L("Контур платы", "Board outline"), 1);
            else if (strlen(e) >= 2 && e[0] == 'G' && isdigit(e[1]))
                gf_add(p, e, Lf("Медь, внутренний слой {0}", "Inner copper {0}", strsub(e, 1), "", ""), 20 + strtol(strsub(e, 1)));
        }
    }
    // внутренние слои по порядку: G1, G2, ...
    int idx[];
    for (i = 0; i < n_in; i++) idx[i] = i;
    for (i = 0; i < n_in; i++)
        for (k = i + 1; k < n_in; k++)
            if (inner_no[idx[k]] < inner_no[idx[i]]) { int tmp = idx[i]; idx[i] = idx[k]; idx[k] = tmp; }
    for (i = 0; i < n_in; i++)
        gf_add(inner_src[idx[i]], "G" + istr(i + 1), Lf("Медь, внутренний слой {0}", "Inner copper {0}", istr(i + 1), "", ""), 20 + i);
}

int gf_find(string code)
{
    for (int i = 0; i < n_gf; i++)
        if (gf_code[i] == code) return i;
    return -1;
}

// параметр из gerber_job.gbrjob
string job_val(string key)
{
    return json_val(gb_job, key);
}

// ---------------------------------------------------------------- Gerber -> SVG (вывод сразу в текущий output)

real gb_div = 10000.0, gb_unit = 1.0;
int gb_ap_code[];
string gb_ap_type[];
real gb_ap_a[], gb_ap_b[];
int gb_n_ap;
int gs_d01, gs_d03, gs_reg, gs_lp, gs_ap, gs_arc;
real gs_minw;                   // самая узкая апертура штрихов (D01) от 0.05 мм, мм
int gs_thin;                    // штрихов тоньше 0.05 мм (графика, логотипы: изготовитель их не воспроизведёт)
real gs_curw;
real gs_ex1, gs_ey1, gs_ex2, gs_ey2;     // границы нарисованного (центры штрихов и вспышек), мм
int gs_eset;

int ln_hx, ln_hy, ln_hi, ln_hj, ln_d, ln_g;
real ln_x, ln_y, ln_i, ln_j;

void gb_parse_line(string s)
{
    ln_hx = 0; ln_hy = 0; ln_hi = 0; ln_hj = 0; ln_d = -1; ln_g = -1;
    int i = 0, n = strlen(s), j;
    while (i < n) {
        int c = s[i];
        if (c == 'X' || c == 'Y' || c == 'I' || c == 'J' || c == 'D' || c == 'G') {
            j = i + 1;
            while (j < n) {
                int d = s[j];
                if (!(isdigit(d) || d == '-' || d == '+' || d == '.')) break;
                j++;
            }
            real v = strtod(strsub(s, i + 1, j - i - 1));
            if (c == 'X') { ln_x = v; ln_hx = 1; }
            else if (c == 'Y') { ln_y = v; ln_hy = 1; }
            else if (c == 'I') { ln_i = v; ln_hi = 1; }
            else if (c == 'J') { ln_j = v; ln_hj = 1; }
            else if (c == 'D') ln_d = int(v);
            else ln_g = int(v);
            i = j;
        } else i++;
    }
}

int gb_ap_find(int code)
{
    for (int i = 0; i < gb_n_ap; i++)
        if (gb_ap_code[i] == code) return i;
    return -1;
}

// %ADD10R,0.850000X0.200000*%  /  %ADD13C,1.508*%  /  %ADD20OC8,1.2*%
void gb_add_aperture(string s)
{
    int i = 4, n = strlen(s);
    string dn = "";
    while (i < n && isdigit(s[i])) { dn += s[i]; i++; }
    int c = strtol(dn);
    int cm = strstr(s, ",", i);
    string ty;
    if (cm < 0) ty = strsub(s, i, strstr(s, "*", i) - i);
    else ty = strsub(s, i, cm - i);
    string par = "";
    if (cm >= 0) par = strsub(s, cm + 1, strstr(s, "*", cm) - cm - 1);
    string pv[];
    int np = strsplit(pv, par, 'X');
    int k = gb_n_ap++;
    gb_ap_code[k] = c; gb_ap_type[k] = ty;
    gb_ap_a[k] = 0; gb_ap_b[k] = 0;
    if (np > 0) gb_ap_a[k] = strtod(pv[0]) * gb_unit;
    if (np > 1) gb_ap_b[k] = strtod(pv[1]) * gb_unit;
    gs_ap++;
}

string f4(real v)
{
    string s;
    sprintf(s, "%.4f", v);
    return s;
}

// накопитель штрихов одной апертуры
string sk_d = "";
int sk_ap = -1;
string sk_col = "";
real sk_ex = 0, sk_ey = 0;

void sk_flush()
{
    if (sk_d == "") return;
    int a = gb_ap_find(sk_ap);
    real w = 0.1;
    string cap = "round";
    if (a >= 0) {
        w = gb_ap_a[a];
        if (gb_ap_type[a] == "R") { cap = "square"; if (gb_ap_b[a] > 0) w = min(gb_ap_a[a], gb_ap_b[a]); }
    }
    if (w <= 0) w = 0.01;
    printf("<path d=\"%s\" fill=\"none\" stroke=\"%s\" stroke-width=\"%s\" stroke-linecap=\"%s\" stroke-linejoin=\"round\"/>\n",
           sk_d, sk_col, f4(w), cap);
    sk_d = "";
}

// atan2 через atan
real atan2r(real y, real x)
{
    if (x > 0) return atan(y / x);
    if (x < 0 && y >= 0) return atan(y / x) + PI_;
    if (x < 0 && y < 0) return atan(y / x) - PI_;
    if (y > 0) return PI_ / 2;
    if (y < 0) return -PI_ / 2;
    return 0;
}

// дуга от (x0,y0) до (x1,y1) с центром (xc,yc); ccw = против часовой (G03)
string arc_cmd(real x0, real y0, real x1, real y1, real xc, real yc, int ccw)
{
    real r = sqrt((x0 - xc) * (x0 - xc) + (y0 - yc) * (y0 - yc));
    real a0 = atan2r(y0 - yc, x0 - xc), a1 = atan2r(y1 - yc, x1 - xc);
    real span;
    if (ccw) span = a1 - a0; else span = a0 - a1;
    while (span <= 0.000001) span += 2 * PI_;
    string s;
    if (span >= 2 * PI_ - 0.0001) {
        // полная окружность — двумя половинами
        real mx = 2 * xc - x0, my = 2 * yc - y0;
        sprintf(s, "A%s %s 0 1 %d %s %sA%s %s 0 1 %d %s %s", f4(r), f4(r), ccw, f4(mx), f4(my), f4(r), f4(r), ccw, f4(x1), f4(y1));
        return s;
    }
    sprintf(s, "A%s %s 0 %d %d %s %s", f4(r), f4(r), span > PI_, ccw, f4(x1), f4(y1));
    return s;
}

void gb_flash(int ap, real x, real y, string col)
{
    int a = gb_ap_find(ap);
    if (a < 0) return;
    string ty = gb_ap_type[a];
    real p = gb_ap_a[a], q2 = gb_ap_b[a];
    if (ty == "C") {
        printf("<circle cx=\"%s\" cy=\"%s\" r=\"%s\" fill=\"%s\"/>\n", f4(x), f4(y), f4(p / 2), col);
    } else if (ty == "R" || ty == "O") {
        if (q2 <= 0) q2 = p;
        string rx = "";
        if (ty == "O") sprintf(rx, " rx=\"%s\"", f4(min(p, q2) / 2));
        printf("<rect x=\"%s\" y=\"%s\" width=\"%s\" height=\"%s\"%s fill=\"%s\"/>\n", f4(x - p / 2), f4(y - q2 / 2), f4(p), f4(q2), rx, col);
    } else if (ty == "OC8") {
        // восьмиугольник EAGLE: описанный диаметр 1.08239 * d, поворот 22.5°
        real r = p * 1.08239 / 2;
        string pts = "";
        for (int k = 0; k < 8; k++) {
            real an = (22.5 + 45 * k) * PI_ / 180;
            if (pts != "") pts += " ";
            pts += f4(x + r * cos(an)) + "," + f4(y + r * sin(an));
        }
        printf("<polygon points=\"%s\" fill=\"%s\"/>\n", pts, col);
    } else {
        printf("<circle cx=\"%s\" cy=\"%s\" r=\"%s\" fill=\"%s\"/>\n", f4(x), f4(y), f4(max(p, 0.05) / 2), col);
    }
}

// тело слоя: fg — цвет элементов, bg — цвет «светлой» полярности (вырезы)
void gerber_body(string path, string fg, string bg)
{
    string lines[];
    int n = fileread(lines, path);
    gb_div = 10000.0; gb_unit = 1.0; gb_n_ap = 0;
    gs_d01 = 0; gs_d03 = 0; gs_reg = 0; gs_lp = 0; gs_ap = 0; gs_arc = 0; gs_minw = 0; gs_thin = 0; gs_curw = 0; gs_eset = 0;
    int interp = 1, region = 0, dark = 1, cur = -1, last_d = 2, in_am = 0, i;
    int rstarted = 0;
    real cx = 0, cy = 0, nx, ny;
    sk_d = ""; sk_ap = -1; sk_col = fg;
    for (i = 0; i < n; i++) {
        string s = trim(lines[i]);
        if (s == "") continue;
        if (in_am) { if (ends_with(s, "%")) in_am = 0; continue; }
        if (s[0] == '%') {
            if (starts_with(s, "%FS")) {
                int xp = strstr(s, "X");
                if (xp > 0) {
                    int dec = s[xp + 2] - '0';
                    gb_div = pow(10, dec);
                }
            } else if (starts_with(s, "%MO")) {
                if (strstr(s, "IN") >= 0) gb_unit = 25.4; else gb_unit = 1.0;
            } else if (starts_with(s, "%LP")) {
                sk_flush();
                dark = (s[3] == 'D');
                gs_lp++;
            } else if (starts_with(s, "%ADD")) {
                gb_add_aperture(s);
            } else if (starts_with(s, "%AM")) {
                // макрос: продолжается до строки, оканчивающейся на %
                if (!ends_with(s, "%")) in_am = 1;
            }
            continue;
        }
        if (starts_with(s, "G04")) continue;
        if (starts_with(s, "G36")) {
            // регион печатается сразу по ходу разбора: без склейки длинных строк
            sk_flush();
            string rcol = fg;
            if (!dark) rcol = bg;
            printf("<path fill=\"%s\" d=\"", rcol);
            region = 1; rstarted = 0; gs_reg++;
            continue;
        }
        if (starts_with(s, "G37")) {
            if (!rstarted) printf("M%s %s", f4(cx), f4(cy));
            printf("Z\"/>\n");
            region = 0;
            continue;
        }
        if (starts_with(s, "M02") || starts_with(s, "M00")) break;
        gb_parse_line(s);
        if (ln_g == 1) interp = 1;
        else if (ln_g == 2) interp = 2;
        else if (ln_g == 3) interp = 3;
        if (ln_d >= 10) {
            if (ln_d != cur) {
                if (!region) sk_flush();
                cur = ln_d;
                int ca = gb_ap_find(cur);
                gs_curw = 0;
                if (ca >= 0) {
                    gs_curw = gb_ap_a[ca];
                    if (gb_ap_type[ca] == "R" && gb_ap_b[ca] > 0 && gb_ap_b[ca] < gs_curw) gs_curw = gb_ap_b[ca];
                }
            }
            continue;
        }
        if (!ln_hx && !ln_hy && ln_d < 0) continue;
        nx = cx; ny = cy;
        if (ln_hx) nx = ln_x / gb_div * gb_unit;
        if (ln_hy) ny = ln_y / gb_div * gb_unit;
        int d = ln_d;
        if (d < 0) d = last_d;
        last_d = d;
        if (d == 1 || d == 3) {
            if (!gs_eset) { gs_ex1 = nx; gs_ex2 = nx; gs_ey1 = ny; gs_ey2 = ny; gs_eset = 1; }
            if (nx < gs_ex1) gs_ex1 = nx;
            if (nx > gs_ex2) gs_ex2 = nx;
            if (ny < gs_ey1) gs_ey1 = ny;
            if (ny > gs_ey2) gs_ey2 = ny;
        }
        string seg;
        if (d == 1) {
            if (interp == 1) seg = "L" + f4(nx) + " " + f4(ny);
            else {
                real xc = cx + ln_i / gb_div * gb_unit, yc = cy + ln_j / gb_div * gb_unit;
                seg = arc_cmd(cx, cy, nx, ny, xc, yc, interp == 3);
                gs_arc++;
            }
        }
        if (region) {
            if (d == 2) { printf("M%s %s", f4(nx), f4(ny)); rstarted = 1; }
            else if (d == 1) {
                if (!rstarted) { printf("M%s %s", f4(cx), f4(cy)); rstarted = 1; }
                printf("%s", seg);
            }
            cx = nx; cy = ny;
            continue;
        }
        if (d == 2) { cx = nx; cy = ny; continue; }
        string col = fg;
        if (!dark) col = bg;
        if (d == 1) {
            if (sk_ap != cur || sk_col != col || strlen(sk_d) > 6000) {
                sk_flush();
                sk_ap = cur; sk_col = col;
            }
            if (sk_d == "" || abs(sk_ex - cx) > 0.00001 || abs(sk_ey - cy) > 0.00001) sk_d += "M" + f4(cx) + " " + f4(cy);
            sk_d += seg;
            sk_ex = nx; sk_ey = ny;
            gs_d01++;
            if (gs_curw > 0 && gs_curw < 0.05) gs_thin++;
            else if (gs_curw > 0 && (gs_minw == 0 || gs_curw < gs_minw)) gs_minw = gs_curw;
            cx = nx; cy = ny;
        } else if (d == 3) {
            gb_flash(cur, nx, ny, col);
            gs_d03++;
            cx = nx; cy = ny;
        }
    }
    sk_flush();
}

// ---------------------------------------------------------------- Excellon

int n_tool = 0;
int tl_no[], tl_hits[];
real tl_d[];
int n_hole = 0, n_slot = 0;
real hl_x[], hl_y[], hl_d[];

int tl_find(int no)
{
    for (int i = 0; i < n_tool; i++)
        if (tl_no[i] == no) return i;
    return -1;
}

void excellon_parse(string path)
{
    string lines[];
    int n = fileread(lines, path);
    n_tool = 0; n_hole = 0; n_slot = 0;
    real div = 1000.0, unit = 1.0;
    int header = 1, cur = -1, i;
    real px = 0, py = 0;
    for (i = 0; i < n; i++) {
        string s = strupr(trim(lines[i]));
        if (s == "" || s[0] == ';') continue;
        if (starts_with(s, "METRIC") || starts_with(s, "INCH")) {
            if (starts_with(s, "INCH")) unit = 25.4;
            int dp = strstr(s, ".");
            if (dp > 0) {
                int dec = 0;
                for (int k = dp + 1; s[k] == '0'; k++) dec++;
                if (dec > 0) div = pow(10, dec);
            } else if (unit > 1) div = 10000.0;
            continue;
        }
        if (s == "%" || s == "M95") { header = 0; continue; }
        if (s[0] == 'T') {
            int c = strstr(s, "C");
            int no;
            if (c > 0) {
                no = strtol(strsub(s, 1, c - 1));
                if (tl_find(no) < 0) {
                    tl_no[n_tool] = no; tl_d[n_tool] = strtod(strsub(s, c + 1)) * unit; tl_hits[n_tool] = 0;
                    n_tool++;
                }
                if (!header) cur = tl_find(no);
            } else {
                no = strtol(strsub(s, 1));
                cur = tl_find(no);
            }
            continue;
        }
        if (s[0] == 'X' || s[0] == 'Y') {
            int g85 = strstr(s, "G85");
            string a = s, b = "";
            if (g85 >= 0) { a = strsub(s, 0, g85); b = strsub(s, g85 + 3); }
            gb_parse_line(a);
            real x = px, y = py;
            if (ln_hx) { if (strstr(a, ".") >= 0) x = ln_x * unit; else x = ln_x / div * unit; }
            if (ln_hy) { if (strstr(a, ".") >= 0) y = ln_y * unit; else y = ln_y / div * unit; }
            px = x; py = y;
            if (cur >= 0) {
                hl_x[n_hole] = x; hl_y[n_hole] = y; hl_d[n_hole] = tl_d[cur];
                n_hole++;
                tl_hits[cur]++;
                if (b != "") n_slot++;
            }
        }
    }
}

real drill_min()
{
    real m = 0;
    for (int i = 0; i < n_tool; i++)
        if (tl_hits[i] > 0 && (m == 0 || tl_d[i] < m)) m = tl_d[i];
    return m;
}

// ---------------------------------------------------------------- SVG-файлы слоёв

// общее поле для всех слоёв: контур платы + поля
real vb_x, vb_y, vb_w, vb_h;
string vb_flip;

void vb_set(real x1, real y1, real x2, real y2)
{
    real mg = 2.0;
    vb_x = x1 - mg; vb_y = y1 - mg; vb_w = (x2 - x1) + 2 * mg; vb_h = (y2 - y1) + 2 * mg;
    sprintf(vb_flip, "matrix(1 0 0 -1 0 %s)", f4(2 * vb_y + vb_h));
}

void svg_open(int pxw)
{
    int pxh = int(pxw * vb_h / vb_w);
    printf("<svg xmlns=\"http://www.w3.org/2000/svg\" viewBox=\"%s %s %s %s\" width=\"%d\" height=\"%d\">\n",
           f4(vb_x), f4(vb_y), f4(vb_w), f4(vb_h), pxw, pxh);
}

// маска SVG из слоя Gerber: тёмная полярность — белым (видно), светлая — чёрным (вырез)
void mask_from_layer(string src, string id, int inverted)
{
    printf("<mask id=\"%s\" maskUnits=\"userSpaceOnUse\" x=\"%s\" y=\"%s\" width=\"%s\" height=\"%s\">\n", id, f4(vb_x), f4(vb_y), f4(vb_w), f4(vb_h));
    if (inverted) printf("<rect x=\"%s\" y=\"%s\" width=\"%s\" height=\"%s\" fill=\"#fff\"/>\n", f4(vb_x), f4(vb_y), f4(vb_w), f4(vb_h));
    printf("<g transform=\"%s\">\n", vb_flip);
    if (inverted) gerber_body(src, "#000", "#fff");
    else gerber_body(src, "#fff", "#000");
    printf("</g></mask>\n");
}

// маска «тело платы без вскрытий»: контур белым, вскрытия паяльной маски чёрным
void mask_board_minus(string outline, string masksrc, string id)
{
    printf("<mask id=\"%s\" maskUnits=\"userSpaceOnUse\" x=\"%s\" y=\"%s\" width=\"%s\" height=\"%s\">\n", id, f4(vb_x), f4(vb_y), f4(vb_w), f4(vb_h));
    printf("<path transform=\"%s\" fill-rule=\"evenodd\" fill=\"#fff\" d=\"%s\"/>\n", vb_flip, outline);
    if (masksrc != "") {
        printf("<g transform=\"%s\">\n", vb_flip);
        gerber_body(masksrc, "#000", "#fff");
        printf("</g>\n");
    }
    printf("</mask>\n");
}

void full_rect(string fill, string extra)
{
    printf("<rect x=\"%s\" y=\"%s\" width=\"%s\" height=\"%s\" fill=\"%s\"%s/>\n", f4(vb_x), f4(vb_y), f4(vb_w), f4(vb_h), fill, extra);
}

// слой как есть: цвет fg, вырезы прозрачные
void write_layer_svg(string src, string dst, string fg)
{
    output(dst, "wt") {
        svg_open(1200);
        printf("<defs>\n");
        mask_from_layer(src, "l", 0);
        printf("</defs>\n");
        full_rect(fg, " mask=\"url(#l)\"");
        printf("</svg>\n");
    }
}

// слой на сплошном фоне без масок: вырезы закрашиваются цветом фона.
// Так картинка одинаково выглядит в любом браузере, PDF и на принтере.
void write_flat_svg(string src, string dst, string fg, string bg)
{
    output(dst, "wt") {
        svg_open(1200);
        full_rect(bg, "");
        printf("<g transform=\"%s\">\n", vb_flip);
        gerber_body(src, fg, bg);
        printf("</g></svg>\n");
    }
}

// вид платы одним рисунком без масок (порядок «художника»):
// основа, медь (вырезы — цвет основы), полупрозрачная маска, вскрытия цветом покрытия,
// шелкография (её вырезы — цвет маски), отверстия
void write_composite_svg(string dst, string cu, string mk, string sk, string outline, string mc, string sc, string fc, string bg)
{
    string sub = "#b9a46a";
    output(dst, "wt") {
        svg_open(1200);
        if (bg != "") full_rect(bg, "");
        printf("<path transform=\"%s\" fill-rule=\"evenodd\" fill=\"%s\" d=\"%s\"/>\n", vb_flip, sub, outline);
        if (cu != "") { printf("<g transform=\"%s\">\n", vb_flip); gerber_body(cu, "#c98b3c", sub); printf("</g>\n"); }
        if (mk != "") {
            printf("<path transform=\"%s\" fill-rule=\"evenodd\" fill=\"%s\" fill-opacity=\"0.86\" d=\"%s\"/>\n", vb_flip, mc, outline);
            printf("<g transform=\"%s\">\n", vb_flip); gerber_body(mk, fc, mc); printf("</g>\n");
        }
        if (sk != "") { printf("<g transform=\"%s\">\n", vb_flip); gerber_body(sk, sc, mc); printf("</g>\n"); }
        printf("<g transform=\"%s\">\n", vb_flip);
        for (int i = 0; i < n_hole; i++)
            printf("<circle cx=\"%s\" cy=\"%s\" r=\"%s\" fill=\"#0d1014\"/>\n", f4(hl_x[i]), f4(hl_y[i]), f4(hl_d[i] / 2));
        printf("</g>\n");
        printf("<path transform=\"%s\" fill=\"none\" stroke=\"#000\" stroke-opacity=\".35\" stroke-width=\"0.15\" d=\"%s\"/>\n", vb_flip, outline);
        printf("</svg>\n");
    }
}

// паяльная маска «как на плате»: цвет маски по контуру, вскрытия прозрачные
void write_mask_svg(string src, string dst, string outline, string color)
{
    output(dst, "wt") {
        svg_open(1200);
        printf("<defs>\n");
        mask_board_minus(outline, src, "m");
        printf("</defs>\n");
        full_rect(color, " fill-opacity=\"0.84\" mask=\"url(#m)\"");
        printf("</svg>\n");
    }
}

// открытая медь (покрытие): медь, видимая во вскрытиях маски
void write_finish_svg(string copper, string masksrc, string dst, string color)
{
    output(dst, "wt") {
        svg_open(1200);
        printf("<defs>\n");
        mask_from_layer(copper, "c", 0);
        mask_from_layer(masksrc, "o", 0);
        printf("</defs>\n<g mask=\"url(#o)\">\n");
        full_rect(color, " mask=\"url(#c)\"");
        printf("</g>\n</svg>\n");
    }
}

// шелкография только по маске (JLCPCB срезает её с площадок)
void write_silk_svg(string silk, string masksrc, string outline, string dst, string color)
{
    output(dst, "wt") {
        svg_open(1200);
        printf("<defs>\n");
        mask_from_layer(silk, "s", 0);
        mask_board_minus(outline, masksrc, "b");
        printf("</defs>\n<g mask=\"url(#b)\">\n");
        full_rect(color, " mask=\"url(#s)\"");
        printf("</g>\n</svg>\n");
    }
}

// основа платы (стеклотекстолит) по контуру
void write_substrate_svg(string dst, string outline, string color)
{
    output(dst, "wt") {
        svg_open(1200);
        printf("<path transform=\"%s\" fill-rule=\"evenodd\" fill=\"%s\" stroke=\"#000\" stroke-opacity=\".35\" stroke-width=\"0.15\" d=\"%s\"/>\n",
               vb_flip, color, outline);
        printf("</svg>\n");
    }
}

// отверстия
void write_drill_svg(string dst, string fill, string ring)
{
    output(dst, "wt") {
        svg_open(1200);
        printf("<g transform=\"%s\">\n", vb_flip);
        for (int i = 0; i < n_hole; i++)
            printf("<circle cx=\"%s\" cy=\"%s\" r=\"%s\" fill=\"%s\" stroke=\"%s\" stroke-width=\"0.04\"/>\n",
                   f4(hl_x[i]), f4(hl_y[i]), f4(hl_d[i] / 2), fill, ring);
        printf("</g></svg>\n");
    }
}

// цвета маски и шелкографии по названию опции JLC
string mask_rgb(string m)
{
    m = strupr(m);
    if (strstr(m, "RED") >= 0) return "#a31b1b";
    if (strstr(m, "BLUE") >= 0) return "#1b3f9e";
    if (strstr(m, "BLACK") >= 0) return "#151515";
    if (strstr(m, "WHITE") >= 0) return "#f2f2f2";
    if (strstr(m, "YELLOW") >= 0) return "#d8b616";
    if (strstr(m, "PURPLE") >= 0) return "#5b2a86";
    return "#0f6b3a";
}

string silk_rgb(string m)
{
    if (strstr(strupr(m), "BLACK") >= 0) return "#111111";
    return "#ffffff";
}

string finish_rgb(string f)
{
    f = strupr(f);
    if (strstr(f, "ENIG") >= 0 || strstr(f, "GOLD") >= 0) return "#e2b64e";
    if (strstr(f, "OSP") >= 0) return "#d58a4f";
    return "#c9c9c9";
}

// fk_core.ulp — версия, настройки, язык интерфейса, файлы, состояние между фазами
// dmxON FabKit · dmxON by AlexSmith 2026 · см. LICENSE.md

// ---------------------------------------------------------------- продукт

string FK_NAME    = "dmxON FabKit";
string FK_VERSION = "2.6.0";              // при каждой переделке поднимать (см. CHANGELOG.md)
string FK_DATE    = "2026-10-16";
string FK_AUTHOR  = "dmxON by AlexSmith";
string FK_YEAR    = "2026";
string FK_ID      = "dmxon_fabkit";       // префикс настроек в eaglerc
string FK_MARKER  = ".dmxon-fabkit";      // метка «эта папка создана FabKit» — только такую можно очищать
string FK_REPO    = "https://github.com/AlexSmith2025/dmxON-FabKit-Fusion-Electronics";
string FK_DONATE  = "https://www.paypal.com/donate/?business=smith.show2025%40gmail.com&no_recurring=0&item_name=dmxON+FabKit&currency_code=EUR";

string fk_title()
{
    return FK_NAME + " v" + FK_VERSION;
}

string fk_sign()
{
    return FK_NAME + " v" + FK_VERSION + " · " + FK_AUTHOR + " " + FK_YEAR;
}

// ---------------------------------------------------------------- адреса каталогов

string LCSC_HEADER  = "JLCPCB Part #";
string JLC_API      = "https://jlcpcb.com/api/overseas-pcb-order/v1/shoppingCart/smtGood/selectSmtComponentList";
string JLCSEARCH    = "https://jlcsearch.tscircuit.com";
int    NET_TIMEOUT  = 25;

// ---------------------------------------------------------------- настройки (запоминаются в eaglerc)

string opt_root      = "";     // куда выгружать
int    opt_open      = 1;      // открыть папку после выгрузки
int    opt_backup    = 1;      // бэкап проекта в 05_BACKUP пакета (общий ключ dmxon.backup), по умолчанию включён
int    opt_online    = 1;      // искать номера в каталогах
int    opt_basic     = 1;      // предпочитать Basic/Preferred
int    opt_tht       = 1;      // выгружать выводные детали
int    opt_centroid  = 0;      // CPL по центру площадок (если посадочное место не сверено)
int    opt_writeattr = 0;      // записать найденные номера в атрибут LCSC_PART
int    opt_fixattr   = 0;      // номер из атрибута не совпал с номиналом -> подобрать по номиналу
int    opt_geo       = 1;      // сверять посадочные места с JLC, поворот и центр — по ним
int    opt_alt       = 1;      // подставлять совместимые замены вместо отсутствующих деталей
int    opt_boards    = 5;      // плат в заказе
int    opt_minv      = 16;     // минимальное напряжение конденсаторов, В
string opt_fee       = "3";    // плата за установку катушки Extended, $
string opt_prefixes  = "H,MH,FID,FD,SJ,TP";
int    opt_gerber    = 1;      // Gerber + сверловка для JLCPCB
int    opt_docs      = 1;      // документация для ручной сборки (A4)
int    opt_toner     = 1;      // PDF 1:1 для ЛУТ
int    opt_pdf       = 1;      // HTML -> PDF через Microsoft Edge
string opt_thick     = "1.6";  // толщина платы для заказа, мм
string opt_mask      = "Green";
string opt_silk      = "White";
string opt_finish    = "HASL (with lead)";
int    batch_mode    = 0;

// штамп (заполняется в диалоге, хранится отдельно для каждой платы)
string tb_product = "", tb_docno = "", tb_company = "", tb_designer = "", tb_checker = "";
string tb_approver = "", tb_customer = "", tb_rev = "1.0", tb_note = "";

// ---------------------------------------------------------------- версия платы (одна на всё)
// Источник — глобальный атрибут проекта REV (общий для схемы и платы, переезжает вместе с проектом);
// поле «Версия» на вкладке штампа его меняет. Версия входит в имя папки пакета и всех файлов
// (<плата>_v<версия>_…), в имена Gerber, штампы листов и заголовки отчёта.

// «Rev 1.4», «Ver. 1.4», «v1.4», «1.4» -> «1.4»; только буквы, цифры, «.», «-», «_»
string rev_norm(string r)
{
    r = trim(r);
    string u = strupr(r);
    if (starts_with(u, "REVISION")) r = strsub(r, 8);
    else if (starts_with(u, "VERSION")) r = strsub(r, 7);
    else if (starts_with(u, "REV") || starts_with(u, "VER")) r = strsub(r, 3);
    else if (starts_with(u, "V") && strlen(r) > 1 && isdigit(r[1])) r = strsub(r, 1);
    while (r != "" && (r[0] == '.' || r[0] == ' ' || r[0] == ':' || r[0] == '_')) r = strsub(r, 1);
    string t = "";
    for (int i = 0; r[i]; i++) {
        int c = r[i];
        if ((c >= 'a' && c <= 'z') || (c >= 'A' && c <= 'Z') || (c >= '0' && c <= '9') || c == '.' || c == '-' || c == '_') t += r[i];
        else if (c == ' ') t += "-";
    }
    return t;
}

// суффикс имени файла: «_v1.4» или ""
string ver_tag(string r)
{
    string n = rev_norm(r);
    if (n == "") return "";
    return "_v" + n;
}

// подпись для заголовков: «EncBoard v1.4»
string ver_disp(string base, string r)
{
    string n = rev_norm(r);
    if (n == "") return base;
    return base + " v" + n;
}

// версия в тексте платы: «Encoder Ver. 1.4» -> «1.4», иначе ""
string text_version(string s)
{
    string u = strupr(s);
    int p = strstr(u, "VER");
    if (p < 0) p = strstr(u, "REV");
    if (p < 0) return "";
    int i = p + 3;
    while (u[i] && isalpha(u[i])) i++;
    while (u[i] && (u[i] == '.' || u[i] == ' ' || u[i] == ':')) i++;
    string v = "";
    while (u[i] && (isdigit(u[i]) || u[i] == '.')) { v += s[i]; i++; }
    while (v != "" && v[strlen(v) - 1] == '.') v = strsub(v, 0, strlen(v) - 1);
    if (v == "" || !isdigit(v[0])) return "";
    return v;
}
string tb_pcbno = "";            // обозначение печатной платы (детали)

real fee_usd()
{
    return strtod(opt_fee);
}


// ---------------------------------------------------------------- язык интерфейса
// Английский по умолчанию. Русский и английский тексты — прямо в коде (L("рус", "eng")),
// испанский, немецкий и польский — из таблицы lib/fk_lang.ulp, ключ — английский текст.
// Выбор языка общий для dmxON FabKit и dmxON JLC Rules (настройка dmxon.lang).
string LANG_CODE[] = { "en", "ru", "es", "de", "pl" };
string LANG_NAME[] = { "English", "Русский", "Español", "Deutsch", "Polski" };
int    N_LANG   = 5;
int    ui_lang  = 0;                      // 0 en, 1 ru, 2 es, 3 de, 4 pl
string LANG_CFG = "dmxon.lang";

void lang_load()
{
    string c = cfgget(LANG_CFG, "en");
    ui_lang = 0;
    for (int i = 0; i < N_LANG; i++) if (LANG_CODE[i] == c) ui_lang = i;
}

void lang_save()
{
    cfgset(LANG_CFG, LANG_CODE[ui_lang]);
}

// код языка из аргумента -lang
int lang_index(string c)
{
    for (int i = 0; i < N_LANG; i++) if (LANG_CODE[i] == strlwr(c)) return i;
    return -1;
}

// ---------------------------------------------------------------- стандарт документации
// ISO — ISO 5457 / ISO 7200 / ISO 7573 / IEC 81346 и IPC; ГОСТ — ЕСКД (ГОСТ Р 2.104-2023 и др.).
// Выбор общий для dmxON FabKit и dmxON JLC Rules (настройка dmxon.std).
string STD_CODE[] = { "iso", "gost" };
string STD_NAME[] = { "ISO", "ГОСТ" };
int N_STD = 2;
int doc_std = 0;                 // 0 ISO, 1 ГОСТ
string STD_CFG = "dmxon.std";

void std_load()
{
    string c = cfgget(STD_CFG, "iso");
    doc_std = 0;
    for (int i = 0; i < N_STD; i++) if (STD_CODE[i] == c) doc_std = i;
}

void std_save()
{
    cfgset(STD_CFG, STD_CODE[doc_std]);
}

int std_index(string c)
{
    c = strlwr(c);
    if (c == "гост") c = "gost";
    for (int i = 0; i < N_STD; i++) if (STD_CODE[i] == c) return i;
    return -1;
}

int TR_HT[];
int tr_built = 0;

int tr_hash(string s)
{
    int hv = 7;
    for (int i = 0; s[i]; i++) hv = (hv * 31 + s[i]) % 1000003;
    return hv % 4099;
}

void tr_build()
{
    for (int i = 0; i < TR_N; i++) {
        int b = tr_hash(TR_EN[i]);
        while (TR_HT[b]) b = (b + 1) % 4099;
        TR_HT[b] = i + 1;
    }
    tr_built = 1;
}

// английский текст на языке lg (2 es, 3 de, 4 pl); перевода нет — остаётся английский
string tr(int lg, string en)
{
    if (!tr_built) tr_build();
    int b = tr_hash(en);
    while (TR_HT[b]) {
        int i = TR_HT[b] - 1;
        if (TR_EN[i] == en) {
            string v = lg == 2 ? TR_ES[i] : (lg == 3 ? TR_DE[i] : TR_PL[i]);
            return v != "" ? v : en;
        }
        b = (b + 1) % 4099;
    }
    return en;
}

// текст на языке lg
string Lx(int lg, string ru, string en)
{
    if (lg == 1) return ru;
    if (lg == 0) return en;
    return tr(lg, en);
}

// текст на языке интерфейса
string L(string ru, string en)
{
    return Lx(ui_lang, ru, en);
}

string fmt3(string s, string a, string b, string c)
{
    s = replace_all(s, "{0}", a);
    s = replace_all(s, "{1}", b);
    return replace_all(s, "{2}", c);
}

// шаблон с подстановками {0} {1} {2}
string Lf(string ru, string en, string a, string b, string c)
{
    return fmt3(L(ru, en), a, b, c);
}

string Lfx(int lg, string ru, string en, string a, string b, string c)
{
    return fmt3(Lx(lg, ru, en), a, b, c);
}

// для HTML: подпись на языке интерфейса
string hl(string ru, string en)
{
    return h(L(ru, en));
}

// готовая разметка: не-ASCII символы -> числовые ссылки (теги и сущности не трогает)
string asc(string s)
{
    string t = "";
    int i = 0, from = 0;
    while (s[i]) {
        if (s[i] > 127) {
            if (i > from) t += strsub(s, from, i - from);
            string e;
            sprintf(e, "&#%d;", s[i]);
            t += e;
            from = i + 1;
        }
        i++;
    }
    if (from == 0) return s;
    if (i > from) t += strsub(s, from, i - from);
    return t;
}

// то же в строке текста
string hs(string ru, string en)
{
    return h(L(ru, en));
}

// ---------------------------------------------------------------- файлы и команды

int file_exists(string p)
{
    string a[];
    return fileglob(a, p) > 0;
}

// Команды Windows выполняются без окон: через маленький VBS-запускальщик (wscript — оконная
// программа, консоль не открывает). В Windows 11 иначе каждый вызов открывает окно Терминала.
// Кавычки в команде передаются как ` и восстанавливаются в запускальщике.
string fk_runner = "";

string RUNNER_VBS =
    "Option Explicit\r\n" +
    "Dim sh, fso, mode, a, i, last, sz\r\n" +
    "Set sh = CreateObject(\"WScript.Shell\")\r\n" +
    "Set fso = CreateObject(\"Scripting.FileSystemObject\")\r\n" +
    "mode = WScript.Arguments(0)\r\n" +
    "a = Replace(WScript.Arguments(1), \"`\", Chr(34))\r\n" +
    "If mode = \"run\" Then\r\n" +
    "  WScript.Quit sh.Run(\"cmd.exe /s /c \" & Chr(34) & a & Chr(34), 0, True)\r\n" +
    "ElseIf mode = \"wait\" Then\r\n" +
    "  last = -1\r\n" +
    "  For i = 1 To CInt(WScript.Arguments(2)) * 2\r\n" +
    "    If fso.FileExists(a) Then\r\n" +
    "      sz = fso.GetFile(a).Size\r\n" +
    "      If sz > 0 And sz = last Then WScript.Quit 0\r\n" +
    "      last = sz\r\n" +
    "    End If\r\n" +
    "    WScript.Sleep 500\r\n" +
    "  Next\r\n" +
    "  WScript.Quit 1\r\n" +
    "End If\r\n";

// запускальщик кладётся в папку, которая уже есть (временная папка Windows пользователя)
void runner_init(string dir)
{
    if (dir == "") return;
    string p = dir + "/dmxon_fabkit_run.vbs";
    output(p, "wb") printf("%s", RUNNER_VBS);
    if (filesize(p) <= 0) return;
    // Windows Script Host бывает отключён политикой — тогда работаем через cmd.exe
    if (system("wscript.exe //nologo //B \"" + to_win(p) + "\" run \"exit 7\"") == 7) fk_runner = p;
}

int shell(string cmd)
{
    if (fk_runner != "")
        return system("wscript.exe //nologo //B \"" + to_win(fk_runner) + "\" run \"" + replace_all(cmd, "\"", "`") + "\"");
    return system("cmd.exe /c " + cmd);
}

// дождаться файла, пока его размер не перестанет расти (до seconds секунд); 1 — дождались
int wait_file(string path, int seconds)
{
    if (fk_runner != "")
        return system("wscript.exe //nologo //B \"" + to_win(fk_runner) + "\" wait \"" + to_win(path) + "\" " + istr(seconds)) == 0;
    // без запускальщика — короткие паузы через ping
    int last = -1;
    for (int w = 0; w < seconds; w++) {
        if (file_exists(path)) {
            int sz = filesize(path);
            if (sz > 0 && sz == last) return 1;
            last = sz;
        }
        system("cmd.exe /c ping -n 2 127.0.0.1 >nul");
    }
    return file_exists(path);
}

string qp(string p)
{
    return "\"" + to_win(p) + "\"";
}

string url_file(string p)
{
    string s = replace_all(p, "\\", "/");
    s = replace_all(s, " ", "%20");
    s = replace_all(s, "#", "%23");
    return "file:///" + s;
}

// ---------------------------------------------------------------- состояние между фазами (key=value)

string st_k[], st_v[];
int n_st = 0;

void st_set(string k, string v)
{
    for (int i = 0; i < n_st; i++) {
        if (st_k[i] == k) { st_v[i] = v; return; }
    }
    st_k[n_st] = k;
    st_v[n_st] = v;
    n_st++;
}

void st_seti(string k, int v)
{
    st_set(k, istr(v));
}

string st_get(string k)
{
    for (int i = 0; i < n_st; i++)
        if (st_k[i] == k) return st_v[i];
    return "";
}

int st_geti(string k)
{
    return strtol(st_get(k));
}

void st_save(string path)
{
    output(path, "wt") {
        for (int i = 0; i < n_st; i++) {
            string v = replace_all(st_v[i], "\n", "\\n");
            printf("%s=%s\n", st_k[i], h(v));
        }
    }
}

// символ по коду Юникода: char в ULP 8-битный, поэтому берём символ из таблиц-литералов
string UNI_CYR = "ЀЁЂЃЄЅІЇЈЉЊЋЌЍЎЏАБВГДЕЖЗИЙКЛМНОПРСТУФХЦЧШЩЪЫЬЭЮЯабвгдежзийклмнопрстуфхцчшщъыьэюяѐёђѓєѕіїјљњћќѝўџѠѡѢѣѤѥѦѧѨѩѪѫѬѭѮѯѰѱѲѳѴѵѶѷѸѹѺѻѼѽѾѿҀҁ҂҃҄҅҆҇҈҉ҊҋҌҍҎҏҐґҒғҔҕҖҗҘҙҚқҜҝҞҟҠҡҢңҤҥҦҧҨҩҪҫҬҭҮүҰұҲҳҴҵҶҷҸҹҺһҼҽҾҿӀӁӂӃӄӅӆӇӈӉӊӋӌӍӎӏӐӑӒӓӔӕӖӗӘәӚӛӜӝӞӟӠӡӢӣӤӥӦӧӨөӪӫӬӭӮӯӰӱӲӳӴӵӶӷӸӹӺӻӼӽӾӿ";
string UNI_LAT = " ¡¢£¤¥¦§¨©ª«¬­®¯°±²³´µ¶·¸¹º»¼½¾¿ÀÁÂÃÄÅÆÇÈÉÊËÌÍÎÏÐÑÒÓÔÕÖ×ØÙÚÛÜÝÞßàáâãäåæçèéêëìíîïðñòóôõö÷øùúûüýþÿ";
string UNI_LXA = "ĀāĂăĄąĆćĈĉĊċČčĎďĐđĒēĔĕĖėĘęĚěĜĝĞğĠġĢģĤĥĦħĨĩĪīĬĭĮįİıĲĳĴĵĶķĸĹĺĻļĽľĿŀŁłŃńŅņŇňŉŊŋŌōŎŏŐőŒœŔŕŖŗŘřŚśŜŝŞşŠšŢţŤťŦŧŨũŪūŬŭŮůŰűŲųŴŵŶŷŸŹźŻżŽžſ";
string UNI_PUN = "–—‘’“”„•…№™←↑→↓−≤≥≈≠×‰€′″";
int UNI_PUN_CODE[] = { 8211, 8212, 8216, 8217, 8220, 8221, 8222, 8226, 8230, 8470, 8482, 8592, 8593, 8594, 8595, 8722, 8804, 8805, 8776, 8800, 215, 8240, 8364, 8242, 8243 };

string uchar(int c)
{
    if (c < 128) { char a = c; string t = ""; t += a; return t; }
    if (c >= 0x400 && c < 0x500) return strsub(UNI_CYR, c - 0x400, 1);
    if (c >= 0xA0 && c < 0x100) return strsub(UNI_LAT, c - 0xA0, 1);
    if (c >= 0x100 && c < 0x180) return strsub(UNI_LXA, c - 0x100, 1);
    for (int i = 0; i < 25; i++)
        if (UNI_PUN_CODE[i] == c) return strsub(UNI_PUN, i, 1);
    return "?";
}

// значения пишутся через h(): так кириллица и спецсимволы переживают однобайтовую кодировку
string unh(string s)
{
    string t = "";
    int i = 0;
    while (s[i]) {
        if (s[i] == '&') {
            int e = strstr(s, ";", i);
            if (e > i) {
                string ent = strsub(s, i + 1, e - i - 1);
                if (ent == "amp") t += "&";
                else if (ent == "lt") t += "<";
                else if (ent == "gt") t += ">";
                else if (ent == "quot") t += "\"";
                else if (ent[0] == '#') t += uchar(strtol(strsub(ent, 1))); else t += "&" + ent + ";";
                i = e + 1;
                continue;
            }
        }
        t += s[i];
        i++;
    }
    return t;
}

void st_load(string path)
{
    string lines[];
    n_st = 0;
    if (!file_exists(path)) return;
    int n = fileread(lines, path);
    for (int i = 0; i < n; i++) {
        int p = strstr(lines[i], "=");
        if (p <= 0) continue;
        st_k[n_st] = strsub(lines[i], 0, p);
        st_v[n_st] = replace_all(unh(trim(strsub(lines[i], p + 1))), "\\n", "\n");
        n_st++;
    }
}

// ---------------------------------------------------------------- журнал хода работы (для отчёта)

string log_txt = "";

void fk_log(string s)
{
    log_txt += t2string(time(), "hh:mm:ss") + "  " + s + "\n";
    status(FK_NAME + ": " + s);
}

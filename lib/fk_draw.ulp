// fk_draw.ulp — геометрия платы и чертежи сборки (SVG): контур, корпуса, площадки, ключи, шаги пайки
// dmxON FabKit · dmxON by AlexSmith 2026 · см. LICENSE.md

// ---------------------------------------------------------------- контур платы

string ol_path = "";          // контур платы (слой 20), координаты платы в мм
string ol_circ = "";          // круглые вырезы
real bb_x1 = 0, bb_y1 = 0, bb_x2 = 0, bb_y2 = 0;
int bb_set = 0;

void bb_add(real x, real y)
{
    if (!bb_set) { bb_x1 = x; bb_x2 = x; bb_y1 = y; bb_y2 = y; bb_set = 1; return; }
    if (x < bb_x1) bb_x1 = x;
    if (x > bb_x2) bb_x2 = x;
    if (y < bb_y1) bb_y1 = y;
    if (y > bb_y2) bb_y2 = y;
}

// отрезок или дуга в формате SVG path (координаты в мм, ось Y вверх)
string seg_path(real x1, real y1, real x2, real y2, real curve)
{
    string s;
    if (curve == 0) {
        sprintf(s, "M%s %sL%s %s", f3(x1), f3(y1), f3(x2), f3(y2));
        return s;
    }
    real ch = sqrt((x2 - x1) * (x2 - x1) + (y2 - y1) * (y2 - y1));
    real a = curve;
    if (a < 0) a = -a;
    real r = ch / (2 * sin(a * PI_ / 360.0));
    int large = (a > 180);
    int sweep = (curve > 0);
    sprintf(s, "M%s %sA%s %s 0 %d %d %s %s", f3(x1), f3(y1), f3(r), f3(r), large, sweep, f3(x2), f3(y2));
    return s;
}

// ---------------------------------------------------------------- элементы

string el_gfx[];              // графика корпуса (tPlace/tDocu): path d
string el_circ[];             // окружности корпуса: готовые <circle>
string el_pads[];             // площадки: готовые SVG-элементы (координаты платы)
real el_p1x[], el_p1y[];      // вывод 1 (или катод) на плате
int el_has_p1[], el_p1cat[];  // есть ли ключ; 1 = это катод
real el_bx1[], el_by1[], el_bx2[], el_by2[];
real el_pitch[];              // минимальный шаг выводов, мм
int el_npads[];

void el_bb_add(int e, real x, real y)
{
    if (x < el_bx1[e]) el_bx1[e] = x;
    if (x > el_bx2[e]) el_bx2[e] = x;
    if (y < el_by1[e]) el_by1[e] = y;
    if (y > el_by2[e]) el_by2[e] = y;
}

void el_draw_init(int e)
{
    el_gfx[e] = ""; el_circ[e] = ""; el_pads[e] = "";
    el_has_p1[e] = 0; el_p1cat[e] = 0; el_p1x[e] = 0; el_p1y[e] = 0;
    el_bx1[e] = 1000000.0; el_by1[e] = 1000000.0; el_bx2[e] = -1000000.0; el_by2[e] = -1000000.0;
    el_pitch[e] = 0; el_npads[e] = 0;
}

// площадка в SVG (координаты платы)
string pad_svg(real x, real y, real w, real hh, real rot, int rnd)
{
    string s;
    if (rnd) sprintf(s, "<circle cx=\"%s\" cy=\"%s\" r=\"%s\"/>", f3(x), f3(y), f3(w / 2));
    else sprintf(s, "<rect x=\"%s\" y=\"%s\" width=\"%s\" height=\"%s\" transform=\"translate(%s %s) rotate(%s)\"/>",
                 f3(-w / 2), f3(-hh / 2), f3(w), f3(hh), f3(x), f3(y), f3(rot));
    return s;
}

// катод диода/светодиода: площадка с таким именем
int is_cathode_name(string n)
{
    n = strupr(trim(n));
    return n == "C" || n == "K" || n == "KA" || n == "CATHODE" || n == "-";
}

// ---------------------------------------------------------------- шаги пайки

int STEP_N = 7;

string step_txt(int s)
{
    if (s == 1) return L("Нижняя сторона: SMD-компоненты", "Bottom side: SMD parts");
    if (s == 2) return L("Микросхемы с мелким шагом (QFN, QFP, шаг ≤ 0.65 мм)", "Fine-pitch ICs (QFN, QFP, pitch ≤ 0.65 mm)");
    if (s == 3) return L("Прочие микросхемы и транзисторы (SOIC, SOT, TSSOP)", "Other ICs and transistors (SOIC, SOT, TSSOP)");
    if (s == 4) return L("Мелкие пассивные компоненты (0201–0805)", "Small passives (0201–0805)");
    if (s == 5) return L("Остальные SMD: 1206+, диоды, светодиоды, кварцы", "Other SMD: 1206+, diodes, LEDs, crystals");
    if (s == 6) return L("Крупные SMD: электролиты, силовые дроссели, SMD-разъёмы", "Bulky SMD: electrolytics, power inductors, SMD connectors");
    return L("Выводные компоненты (THT) — в последнюю очередь", "Through-hole parts (THT) — last");
}

string step_tip(int s)
{
    if (s == 1) return L("Паяйте первой сторону с меньшим числом и массой деталей.", "Solder the side with fewer and lighter parts first.");
    if (s == 2) return L("Флюс, паяльная паста или волна по выводам; проверить мосты под лупой. Центральную площадку — феном.",
                         "Flux and paste or drag-solder; inspect for bridges. Exposed pad — hot air.");
    if (s == 3) return L("Сначала прихватить один вывод, выровнять по ключу, затем пропаять остальные.", "Tack one pin, align to the pin-1 key, then solder the rest.");
    if (s == 4) return L("Пинцет и тонкое жало; одна сторона — прихват, затем вторая.", "Tweezers and a fine tip; tack one side, then the other.");
    if (s == 5) return L("Соблюдать полярность диодов и светодиодов (метка катода).", "Mind diode and LED polarity (cathode mark).");
    if (s == 6) return L("Учесть теплоёмкость: прогрев сильнее, полярность электролитов.", "Large thermal mass: more heat; electrolytic polarity.");
    return L("Выводные — последними, после отмывки SMD; низкие раньше высоких.", "THT parts last, after cleaning SMD; low parts before tall ones.");
}

int el_step[];

int calc_step(int e)
{
    if (el_bottom[e] && !el_tht[e]) return 1;
    if (el_tht[e]) return 7;
    string p = des_prefix(el_name[e]);
    real w = el_bx2[e] - el_bx1[e], hh = el_by2[e] - el_by1[e];
    real area = w * hh;
    int ic = (p == "U" || p == "IC" || p == "DA" || p == "DD" || p == "Q" || p == "VT" || p == "T" || p == "VR");
    if (el_npads[e] >= 8 && el_pitch[e] > 0 && el_pitch[e] <= 0.66) return 2;
    if (ic || el_npads[e] >= 3) {
        if (area > 60) return 6;
        return 3;
    }
    if (el_npads[e] <= 2 && (p == "R" || p == "C" || p == "L" || p == "FB")) {
        string j = el_jpkg[e];
        if (j == "01005" || j == "0201" || j == "0402" || j == "0603" || j == "0805") return 4;
    }
    if (area > 30) return 6;
    return 5;
}

// номинал похож на сопротивление или ёмкость (33R, 4k7, 10K, 1M, 100n, 4.7uF)
int passive_value(string v)
{
    string u = strupr(squeeze(v));
    if (u == "" || !isdigit(u[0])) return 0;
    int letters = 0;
    for (int i = 0; u[i]; i++) {
        char c = u[i];
        if (isdigit(c) || c == '.' || c == ',') continue;
        if (c == 'R' || c == 'K' || c == 'M' || c == 'U' || c == 'N' || c == 'P' || c == 'F' || c == 'H') { letters++; continue; }
        return 0;
    }
    return letters > 0 && letters <= 3;
}

int needs_key(int e)
{
    string p = des_prefix(el_name[e]);
    if (el_npads[e] <= 2 && is_chip(el_jpkg[e]) && passive_value(el_value[e]) && p != "D" && p != "LED" && p != "VD" && p != "HL") return 0;
    if (p == "R" || p == "RN" || p == "RA" || p == "L" || p == "FB" || p == "F" || p == "Y" || p == "X" || p == "J" || p == "S" || p == "SW") return 0;
    if (p == "C" && el_npads[e] <= 2) {
        // керамика — без ключа; электролит/тантал — по корпусу
        string j = strupr(el_jpkg[e]);
        if (strstr(j, "CASE-") >= 0) return 1;
        if (is_chip(el_jpkg[e])) return 0;          // керамика 0402…2512 — без полярности
        if (el_bx2[e] - el_bx1[e] > 4.5) return 1;
        return 0;
    }
    return 1;
}

// ---------------------------------------------------------------- подписи без наложений (чертежи в масштабе)
//
// Каждая подпись — внутри корпуса, если там помещается шрифтом не мельче заданного, иначе рядом
// (сверху, снизу, сбоку, по углам; у высоких корпусов — вертикально), не задевая другие подписи и корпуса.
// Что не поместилось, остаётся без подписи на этом листе — его показывает фрагмент в крупном масштабе.

real lb_x[], lb_y[], lb_fs[];   // центр подписи (мм платы) и высота шрифта
int lb_rot[], lb_ok[];          // 1 — подпись вертикальная; 1 — подпись поставлена
real pl_x1[], pl_y1[], pl_x2[], pl_y2[];
int n_pl = 0;
int lb_side = 0;

// прямоугольник подписи свободен (в пределах поля, без подписей и, если bodies, без чужих корпусов)
int lb_free(int e, real a1, real b1, real a2, real b2, int bodies, real vx0, real vy0, real vx1, real vy1)
{
    if (a1 < vx0 || a2 > vx1 || b1 < vy0 || b2 > vy1) return 0;
    int i;
    for (i = 0; i < n_pl; i++)
        if (a1 < pl_x2[i] && pl_x1[i] < a2 && b1 < pl_y2[i] && pl_y1[i] < b2) return 0;
    if (bodies) {
        for (i = 0; i < n_el; i++) {
            if (i == e || (el_bottom[i] != lb_side && !el_tht[i])) continue;
            if (a1 < el_bx2[i] && el_bx1[i] < a2 && b1 < el_by2[i] && el_by1[i] < b2) return 0;
        }
    }
    return 1;
}

// поставить подпись e в центр (cx, cy) размером w × hh, если место свободно
int lb_put(int e, real cx, real cy, real w, real hh, int rot, real fs, int bodies, real vx0, real vy0, real vx1, real vy1)
{
    real a1 = cx - w / 2, a2 = cx + w / 2, b1 = cy - hh / 2, b2 = cy + hh / 2;
    if (!lb_free(e, a1, b1, a2, b2, bodies, vx0, vy0, vx1, vy1)) return 0;
    pl_x1[n_pl] = a1; pl_y1[n_pl] = b1; pl_x2[n_pl] = a2; pl_y2[n_pl] = b2; n_pl++;
    lb_x[e] = cx; lb_y[e] = cy; lb_rot[e] = rot; lb_fs[e] = fs; lb_ok[e] = 1;
    return 1;
}

// разместить подписи стороны: fsmin/fsmax — высота шрифта в мм платы; v* — поле; возвращает число неразмещённых
int lbl_place(int bottom, real fsmin, real fsmax, real vx0, real vy0, real vx1, real vy1)
{
    lb_side = bottom;
    n_pl = 0;
    numeric string key[];
    int idx[], ord[], n = 0, e, k;
    for (e = 0; e < n_el; e++) {
        lb_ok[e] = 0;
        if (el_bottom[e] != bottom) continue;
        real a = (el_bx2[e] - el_bx1[e]) * (el_by2[e] - el_by1[e]);
        string kk;
        sprintf(kk, "%012.4f", a);
        key[n] = kk;
        idx[n] = e;
        n++;
    }
    sort(n, ord, key);
    // 1) внутри корпусов — самые надёжные места
    for (k = n - 1; k >= 0; k--) {
        e = idx[ord[k]];
        real bw = el_bx2[e] - el_bx1[e], bh = el_by2[e] - el_by1[e];
        int rot = bh > bw * 1.15;
        real lng = rot ? bh : bw, sht = rot ? bw : bh;
        real cw = strlen(el_name[e]) * 0.62 + 0.3;          // ширина подписи в высотах шрифта
        real fs = lng * 0.92 / cw;
        if (fs > sht * 0.8) fs = sht * 0.8;
        if (fs > fsmax) fs = fsmax;
        if (fs < fsmin) continue;
        real w = cw * fs, hh = fs * 0.9;
        lb_put(e, (el_bx1[e] + el_bx2[e]) / 2, (el_by1[e] + el_by2[e]) / 2, rot ? hh : w, rot ? w : hh, rot, fs, 0, vx0, vy0, vx1, vy1);
    }
    // 2) рядом с корпусом, мелкие детали первыми
    int fails = 0;
    for (k = 0; k < n; k++) {
        e = idx[ord[k]];
        if (lb_ok[e]) continue;
        real fs = fsmin, cw = strlen(el_name[e]) * 0.62 + 0.3;
        real w = cw * fs, hh = fs * 0.9, g = fs * 0.2;
        real x1 = el_bx1[e], y1 = el_by1[e], x2 = el_bx2[e], y2 = el_by2[e];
        real cx = (x1 + x2) / 2, cy = (y1 + y2) / 2;
        if (lb_put(e, cx, y2 + g + hh / 2, w, hh, 0, fs, 1, vx0, vy0, vx1, vy1)) continue;
        if (lb_put(e, cx, y1 - g - hh / 2, w, hh, 0, fs, 1, vx0, vy0, vx1, vy1)) continue;
        if (lb_put(e, x2 + g + w / 2, cy, w, hh, 0, fs, 1, vx0, vy0, vx1, vy1)) continue;
        if (lb_put(e, x1 - g - w / 2, cy, w, hh, 0, fs, 1, vx0, vy0, vx1, vy1)) continue;
        if (lb_put(e, x2 + g + hh / 2, cy, hh, w, 1, fs, 1, vx0, vy0, vx1, vy1)) continue;
        if (lb_put(e, x1 - g - hh / 2, cy, hh, w, 1, fs, 1, vx0, vy0, vx1, vy1)) continue;
        if (lb_put(e, x2 + g + w / 2, y2 + g + hh / 2, w, hh, 0, fs, 1, vx0, vy0, vx1, vy1)) continue;
        if (lb_put(e, x1 - g - w / 2, y2 + g + hh / 2, w, hh, 0, fs, 1, vx0, vy0, vx1, vy1)) continue;
        if (lb_put(e, x2 + g + w / 2, y1 - g - hh / 2, w, hh, 0, fs, 1, vx0, vy0, vx1, vy1)) continue;
        if (lb_put(e, x1 - g - w / 2, y1 - g - hh / 2, w, hh, 0, fs, 1, vx0, vy0, vx1, vy1)) continue;
        // чуть дальше — на высоту строки
        if (lb_put(e, cx, y2 + g + hh * 1.5, w, hh, 0, fs, 1, vx0, vy0, vx1, vy1)) continue;
        if (lb_put(e, cx, y1 - g - hh * 1.5, w, hh, 0, fs, 1, vx0, vy0, vx1, vy1)) continue;
        fails++;
    }
    return fails;
}

// ---------------------------------------------------------------- чертёж стороны

// размер подписей в мм платы: отчёт на экране и чертёж в масштабе задают свои пределы
real ds_fsmin = 0.55, ds_fsmax = 2.2;
string ds_wh = "";            // размер чертежа в мм (style), если пусто — в пикселях
int ds_place = 0;             // подписи из lbl_place (чертёж в масштабе)
int ds_crop = 0;              // показать только участок платы ds_v*
real ds_vx0 = 0, ds_vy0 = 0, ds_vx1 = 0, ds_vy1 = 0;
// рамки фрагментов на общем виде: участки платы и их буквы
real tl_x1[], tl_y1[], tl_x2[], tl_y2[];
string tl_lab[];
int n_tl = 0;

// элемент виден в показанном участке
int ds_in(int e)
{
    if (!ds_crop) return 1;
    return el_bx2[e] >= ds_vx0 && el_bx1[e] <= ds_vx1 && el_by2[e] >= ds_vy0 && el_by1[e] <= ds_vy1;
}

// sel: строка вида "|R1|C5|" — выделенные элементы; "" = ничего не выделять
// labels: 0 = подписи только выделенных, 1 = подписи всех
string draw_side(int bottom, string sel, int labels, int pxw)
{
    real mg = 3.0;
    real x0 = bb_x1 - mg, x1 = bb_x2 + mg, y0 = bb_y1 - mg, y1 = bb_y2 + mg;
    if (ds_crop) { x0 = ds_vx0; x1 = ds_vx1; y0 = ds_vy0; y1 = ds_vy1; }
    real W = x1 - x0, H = y1 - y0;
    int pxh = int(pxw * H / W);
    string s, t, tr;
    // сверху: Y вверх -> вниз; снизу: ещё и зеркало по X (вид со стороны пайки)
    if (bottom) sprintf(tr, "matrix(-1 0 0 -1 %s %s)", f3(x1), f3(y1));
    else sprintf(tr, "matrix(1 0 0 -1 %s %s)", f3(-x0), f3(y1));
    if (ds_wh != "") sprintf(s, "<svg class=\"brd\" viewBox=\"0 0 %s %s\" style=\"%s\" xmlns=\"http://www.w3.org/2000/svg\">", f3(W), f3(H), ds_wh);
    else sprintf(s, "<svg class=\"brd\" viewBox=\"0 0 %s %s\" width=\"%d\" height=\"%d\" xmlns=\"http://www.w3.org/2000/svg\">",
                 f3(W), f3(H), pxw, pxh);
    s += "<g transform=\"" + tr + "\">";
    s += "<path class=\"ol\" d=\"" + ol_path + "\"/>" + ol_circ;
    int e;
    // сначала невыделенные (бледно), затем выделенные
    for (int pass = 0; pass < 2; pass++) {
        for (e = 0; e < n_el; e++) {
            if (el_bottom[e] != bottom && !el_tht[e]) continue;
            if (!ds_in(e)) continue;
            if (el_bottom[e] != bottom && el_tht[e]) {
                // выводная с другой стороны видна только площадками
                if (pass == 0) s += "<g class=\"pd0\">" + el_pads[e] + "</g>";
                continue;
            }
            int hi = (sel != "" && strstr(sel, "|" + el_name[e] + "|") >= 0);
            if (pass == 0 && hi) continue;
            if (pass == 1 && !hi) continue;
            string cls = "e0";
            if (hi) cls = "e1";
            else if (sel == "") cls = "e2";
            s += "<g class=\"" + cls + "\"><g class=\"pd\">" + el_pads[e] + "</g>";
            if (el_gfx[e] != "") s += "<path class=\"gx\" d=\"" + el_gfx[e] + "\"/>";
            s += el_circ[e] + "</g>";
        }
    }
    // ключи: вывод 1 / катод
    for (e = 0; e < n_el; e++) {
        if (el_bottom[e] != bottom || !el_has_p1[e] || !ds_in(e) || !needs_key(e)) continue;
        int hi = (sel == "" || strstr(sel, "|" + el_name[e] + "|") >= 0);
        if (!hi) continue;
        real r = 0.35;
        if (el_bx2[e] - el_bx1[e] > 6) r = 0.55;
        sprintf(t, "<circle class=\"k1\" cx=\"%s\" cy=\"%s\" r=\"%s\"/>", f3(el_p1x[e]), f3(el_p1y[e]), f3(r));
        s += t;
    }
    // рамки фрагментов (общий вид)
    for (int q = 0; q < n_tl; q++) {
        sprintf(t, "<rect class=\"tf\" x=\"%s\" y=\"%s\" width=\"%s\" height=\"%s\"/>", f3(tl_x1[q]), f3(tl_y1[q]),
                f3(tl_x2[q] - tl_x1[q]), f3(tl_y2[q] - tl_y1[q]));
        s += t;
    }
    s += "</g>";
    for (q = 0; q < n_tl; q++) {
        real fz = ds_fsmax * 1.6;
        real tx = bottom ? x1 - tl_x2[q] + fz * 0.5 : tl_x1[q] - x0 + fz * 0.5;
        sprintf(t, "<text class=\"tl\" x=\"%s\" y=\"%s\" font-size=\"%s\" style=\"text-anchor:start\">%s</text>", f3(tx), f3(y1 - tl_y2[q] + fz * 1.05), f3(fz), h(tl_lab[q]));
        s += t;
    }
    // подписи (вне трансформации, чтобы текст не зеркалился)
    for (e = 0; e < n_el; e++) {
        if (el_bottom[e] != bottom || !ds_in(e)) continue;
        if (ds_place && sel == "") {
            if (!labels || !lb_ok[e]) continue;
            real px = bottom ? x1 - lb_x[e] : lb_x[e] - x0, py = y1 - lb_y[e];
            string rt = "";
            if (lb_rot[e]) sprintf(rt, " transform=\"rotate(-90 %s %s)\"", f3(px), f3(py));
            sprintf(t, "<text class=\"la\" x=\"%s\" y=\"%s\" font-size=\"%s\"%s>%s</text>", f3(px), f3(py + lb_fs[e] * 0.36), f3(lb_fs[e]), rt, h(el_name[e]));
            s += t;
            continue;
        }
        int hi = (sel != "" && strstr(sel, "|" + el_name[e] + "|") >= 0);
        if (!labels && !hi) continue;
        real cx = (el_bx1[e] + el_bx2[e]) / 2, cy = (el_by1[e] + el_by2[e]) / 2;
        real sx, sy;
        if (bottom) sx = x1 - cx;
        else sx = cx - x0;
        sy = y1 - cy;
        real bw = el_bx2[e] - el_bx1[e], bh = el_by2[e] - el_by1[e];
        real fs = min(bw, bh) * 0.55;
        if (fs < ds_fsmin) fs = ds_fsmin;
        if (fs > ds_fsmax) fs = ds_fsmax;
        if (hi) fs = fs * 1.15;
        string lc = "lb";
        if (hi) lc = "lb1";
        else if (sel != "") lc = "lb0";
        sprintf(t, "<text class=\"%s\" x=\"%s\" y=\"%s\" font-size=\"%s\">%s</text>", lc, f3(sx), f3(sy + fs * 0.35), f3(fs), h(el_name[e]));
        s += t;
    }
    s += "</svg>";
    return s;
}

// ключ микросхемы словами: где вывод 1 относительно центра корпуса (вид сверху)
string key_where(int e)
{
    if (!el_has_p1[e]) return "";
    real cx = (el_bx1[e] + el_bx2[e]) / 2, cy = (el_by1[e] + el_by2[e]) / 2;
    real dx = el_p1x[e] - cx, dy = el_p1y[e] - cy;
    if (el_bottom[e]) dx = -dx;                      // вид со стороны пайки
    real w = (el_bx2[e] - el_bx1[e]) / 2, hh = (el_by2[e] - el_by1[e]) / 2;
    int v = 0, g = 0;
    if (dy > hh * 0.25) v = 1; else if (dy < -hh * 0.25) v = -1;
    if (dx > w * 0.25) g = 1; else if (dx < -w * 0.25) g = -1;
    if (v == 1 && g == -1) return L("слева сверху", "top-left");
    if (v == 1 && g == 1) return L("справа сверху", "top-right");
    if (v == -1 && g == -1) return L("слева снизу", "bottom-left");
    if (v == -1 && g == 1) return L("справа снизу", "bottom-right");
    if (v == 1) return L("сверху", "top");
    if (v == -1) return L("снизу", "bottom");
    if (g == -1) return L("слева", "left");
    if (g == 1) return L("справа", "right");
    return L("в центре", "center");
}

// ключ стрелкой (не зависит от языка): куда смотреть от центра корпуса, вид на эту сторону
string key_arrow(int e)
{
    if (!el_has_p1[e]) return "";
    real cx = (el_bx1[e] + el_bx2[e]) / 2, cy = (el_by1[e] + el_by2[e]) / 2;
    real dx = el_p1x[e] - cx, dy = el_p1y[e] - cy;
    if (el_bottom[e]) dx = -dx;
    real w = (el_bx2[e] - el_bx1[e]) / 2, hh = (el_by2[e] - el_by1[e]) / 2;
    int v = 0, g = 0;
    if (dy > hh * 0.25) v = 1; else if (dy < -hh * 0.25) v = -1;
    if (dx > w * 0.25) g = 1; else if (dx < -w * 0.25) g = -1;
    if (v == 1 && g == -1) return "↖";
    if (v == 1 && g == 1) return "↗";
    if (v == -1 && g == -1) return "↙";
    if (v == -1 && g == 1) return "↘";
    if (v == 1) return "↑";
    if (v == -1) return "↓";
    if (g == -1) return "←";
    if (g == 1) return "→";
    return "•";
}

// нужен ли ключ на чертеже: микросхемы, транзисторы, диоды, светодиоды, полярные конденсаторы
// ---------------------------------------------------------------- сбор геометрии (контекст платы)

// отрезки контура для сборки замкнутой фигуры
real os_x1[], os_y1[], os_x2[], os_y2[], os_cv[];
int n_os = 0;

void outline_add(real x1, real y1, real x2, real y2, real curve)
{
    os_x1[n_os] = x1; os_y1[n_os] = y1; os_x2[n_os] = x2; os_y2[n_os] = y2; os_cv[n_os] = curve;
    n_os++;
    ol_path += seg_path(x1, y1, x2, y2, curve);
    bb_add(x1, y1);
    bb_add(x2, y2);
}

void outline_circle(real x, real y, real r)
{
    string t;
    sprintf(t, "<circle class=\"olc\" cx=\"%s\" cy=\"%s\" r=\"%s\"/>", f3(x), f3(y), f3(r));
    ol_circ += t;
}

// замкнутые контуры из отрезков (жадная сцепка концов), формат SVG path с Z
string outline_closed()
{
    int used[];
    int i, k, n_left = n_os;
    string d = "", seg;
    real tol = 0.02;
    for (i = 0; i < n_os; i++) used[i] = 0;
    while (n_left > 0) {
        int st = -1;
        for (i = 0; i < n_os; i++) if (!used[i]) { st = i; break; }
        if (st < 0) break;
        used[st] = 1; n_left--;
        real sx = os_x1[st], sy = os_y1[st], cx = os_x2[st], cy = os_y2[st];
        d += seg_path(os_x1[st], os_y1[st], os_x2[st], os_y2[st], os_cv[st]);
        int grow = 1;
        while (grow) {
            grow = 0;
            for (k = 0; k < n_os; k++) {
                if (used[k]) continue;
                if (abs(os_x1[k] - cx) < tol && abs(os_y1[k] - cy) < tol) {
                    seg = seg_path(os_x1[k], os_y1[k], os_x2[k], os_y2[k], os_cv[k]);
                    cx = os_x2[k]; cy = os_y2[k];
                } else if (abs(os_x2[k] - cx) < tol && abs(os_y2[k] - cy) < tol) {
                    seg = seg_path(os_x2[k], os_y2[k], os_x1[k], os_y1[k], -os_cv[k]);
                    cx = os_x1[k]; cy = os_y1[k];
                } else continue;
                // убрать начальное M: продолжаем ту же фигуру
                int pa = strstr(seg, "A"), pl = strstr(seg, "L");
                int cut = pl;
                if (pa >= 0 && (pl < 0 || pa < pl)) cut = pa;
                d += strsub(seg, cut);
                used[k] = 1; n_left--;
                grow = 1;
                break;
            }
        }
        if (abs(cx - sx) < tol && abs(cy - sy) < tol) d += "Z";
    }
    return d;
}

void collect_draw(int i, UL_ELEMENT E)
{
    el_draw_init(i);
    int lp = LAYER_TPLACE, ld = 51;
    if (el_bottom[i]) { lp = LAYER_BPLACE; ld = 52; }
    real x1, y1, x2, y2;
    E.footprint.wires(W) {
        x1 = u2mm(W.x1); y1 = u2mm(W.y1); x2 = u2mm(W.x2); y2 = u2mm(W.y2);
        if (W.layer == lp || W.layer == ld) {
            el_gfx[i] += seg_path(x1, y1, x2, y2, W.curve);
            el_bb_add(i, x1, y1);
            el_bb_add(i, x2, y2);
        } else if (W.layer == LAYER_DIMENSION) {
            outline_add(x1, y1, x2, y2, W.curve);
        }
    }
    E.footprint.circles(CI) {
        if (CI.layer == lp || CI.layer == ld) {
            string t;
            sprintf(t, "<circle class=\"gx\" cx=\"%s\" cy=\"%s\" r=\"%s\"/>", f3(u2mm(CI.x)), f3(u2mm(CI.y)), f3(u2mm(CI.radius)));
            el_circ[i] += t;
            el_bb_add(i, u2mm(CI.x) - u2mm(CI.radius), u2mm(CI.y) - u2mm(CI.radius));
            el_bb_add(i, u2mm(CI.x) + u2mm(CI.radius), u2mm(CI.y) + u2mm(CI.radius));
        } else if (CI.layer == LAYER_DIMENSION) {
            outline_circle(u2mm(CI.x), u2mm(CI.y), u2mm(CI.radius));
        }
    }
    E.footprint.rectangles(RC) {
        if (RC.layer == lp || RC.layer == ld) {
            real cx = u2mm(RC.x1 + RC.x2) / 2, cy = u2mm(RC.y1 + RC.y2) / 2;
            real w = u2mm(RC.x2 - RC.x1), hh = u2mm(RC.y2 - RC.y1);
            string t;
            sprintf(t, "<rect class=\"gx\" x=\"%s\" y=\"%s\" width=\"%s\" height=\"%s\" transform=\"translate(%s %s) rotate(%s)\"/>",
                    f3(-w / 2), f3(-hh / 2), f3(abs(w)), f3(abs(hh)), f3(cx), f3(cy), f3(RC.angle));
            el_circ[i] += t;
            el_bb_add(i, cx - abs(w) / 2, cy - abs(hh) / 2);
            el_bb_add(i, cx + abs(w) / 2, cy + abs(hh) / 2);
        }
    }
    // шаг и число выводов — по SMD-площадкам, если они есть (переходные отверстия теплоотвода
    // в QFN/DPAK — тоже «pad», но это не выводы); вывод 1: точное имя «1» главнее «P$1»
    real px[], py[], sx[], sy[];
    int np = 0, ns = 0, p1 = 0, kat = 0, p1rank = 0;
    E.footprint.contacts(C) {
        real x = u2mm(C.x), y = u2mm(C.y), w, hh, rot = 0;
        int rnd = 0;
        if (C.smd) {
            w = u2mm(C.smd.dx); hh = u2mm(C.smd.dy); rot = C.smd.angle;
            rnd = (C.smd.roundness >= 100 && C.smd.dx == C.smd.dy);
            sx[ns] = x; sy[ns] = y; ns++;
        } else {
            w = u2mm(C.pad.diameter[LAYER_TOP]);
            if (w <= 0) w = u2mm(C.pad.drill) * 1.6;
            hh = w; rnd = 1;
        }
        el_pads[i] += pad_svg(x, y, w, hh, rot, rnd);
        real r = max(w, hh) / 2;
        el_bb_add(i, x - r, y - r);
        el_bb_add(i, x + r, y + r);
        px[np] = x; py[np] = y; np++;
        if (is_cathode_name(C.name)) {
            el_p1x[i] = x; el_p1y[i] = y; kat = 1; p1 = 1;
        } else if (!kat) {
            int rk = 0;
            if (C.name == "1") { if (C.smd) rk = 4; else rk = 3; }
            else if (pin_norm(C.name) == "1") { if (C.smd) rk = 2; else rk = 1; }
            if (rk > p1rank) { el_p1x[i] = x; el_p1y[i] = y; p1 = 1; p1rank = rk; }
        }
    }
    if (ns >= 2) {
        np = ns;
        for (int q2 = 0; q2 < ns; q2++) { px[q2] = sx[q2]; py[q2] = sy[q2]; }
    }
    el_npads[i] = np;
    el_has_p1[i] = p1;
    el_p1cat[i] = kat;
    real best = 1000000.0;
    for (int a = 0; a < np; a++) {
        for (int b = a + 1; b < np; b++) {
            real dx = px[a] - px[b], dy = py[a] - py[b];
            real d = sqrt(dx * dx + dy * dy);
            if (d > 0.05 && d < best) best = d;
        }
    }
    if (best < 100000.0) el_pitch[i] = best;
    if (el_bx1[i] > el_bx2[i]) {
        el_bx1[i] = el_x[i] - 0.5; el_bx2[i] = el_x[i] + 0.5; el_by1[i] = el_y[i] - 0.5; el_by2[i] = el_y[i] + 0.5;
    }
}

// fk_lookup.ulp — подбор номера для строки BOM
// dmxON FabKit · dmxON by AlexSmith 2026 · см. LICENSE.md

// ---------------------------------------------------------------- подбор для строки BOM

// резистор или конденсатор по номиналу, корпусу и напряжению
int param_pick(int g, int need)
{
    if (g_kind[g] == 'R') return pick_resistor(g_pval[g], g_jpkg[g], need);
    real vmin = opt_minv;
    if (g_volt[g] > vmin) vmin = g_volt[g];
    int found = pick_capacitor(g_pval[g], g_jpkg[g], vmin, need);
    if (found && pk_volt != "") pk_model += " " + pk_volt;
    return found;
}

void lookup_group(int g)
{
    int need = g_qty[g] * opt_boards;
    int k = g_kind[g];
    int found = 0;
    int param = ((k == 'R' || k == 'C') && g_parsed[g] && is_chip(g_jpkg[g]));

    if (g_lcsc[g] != "") {
        g_src[g] = "атрибут";
        if (!opt_online) return;
        // в первом проходе заранее просим и подбор по номиналу — пригодится, если номер неверный
        if (net_mode == 0 && param && opt_fixattr) param_pick(g, need);
        int vc = verify_code(g_lcsc[g]);
        if (vc < 0) {
            if (net_mode == 1) add_note(g, L("нет ответа от JLCPCB, номер не проверен", "no answer from JLCPCB, part number not verified"));
            return;
        }
        if (vc == 0) {
            add_note(g, Lf("номер {0} не найден в каталоге JLCPCB", "{0} is not in the JLCPCB catalogue", g_lcsc[g], "", ""));
            return;
        }
        g_take_pk(g);
        string vvolt = pk_volt;
        int vstock = pk_stock;

        // не пассив: модель из каталога должна быть похожа на номинал
        if (!param && squeeze(g_value[g]) != "" && pk_model != "") {
            build_cands(g_value[g], "");
            int same = (n_cand == 0);
            string mk = mpn_key(pk_model);
            for (int i = 0; i < n_cand; i++) {
                string ck = mpn_key(cand[i]);
                if (strstr(mk, ck) >= 0 || strstr(ck, mk) >= 0) same = 1;
            }
            if (!same) add_note(g, Lf("проверить: {0}, а номинал {1}", "check: {0}, but the value is {1}",
                                      g_lcsc[g] + " = " + pk_model, squeeze(g_value[g]), ""));
        }

        // номер из атрибута против номинала на схеме
        string bad = "";
        if (k == 'R' && g_parsed[g] && pk_res != "") {
            if (parse_value(ascii_only(pk_res), 'R') && !same_value(pv_value, g_pval[g])) {
                bad = Lf("{0}, а номинал {1}", "{0}, but the value is {1}", g_lcsc[g] + " = " + fmt_value(pv_value, 'R'), fmt_value(g_pval[g], 'R'), "");
            }
        }
        if (k == 'C' && g_parsed[g] && pk_cap != "") {
            if (parse_value(ascii_only(pk_cap), 'C') && !same_value(pv_value, g_pval[g])) {
                bad = Lf("{0}, а номинал {1}", "{0}, but the value is {1}", g_lcsc[g] + " = " + fmt_value(pv_value, 'C'), fmt_value(g_pval[g], 'C'), "");
            }
        }
        if (k == 'C' && vvolt != "" && g_volt[g] > 0) {
            real v = volts_in(ascii_only(vvolt));
            if (v > 0 && v < g_volt[g]) {
                if (bad != "") bad += "; ";
                bad += Lf("{0} на {1} В, нужно {2} В", "{0} is rated {1} V, {2} V required", g_lcsc[g], num(v), num(g_volt[g]));
            }
        }
        if (bad != "" && param && opt_fixattr) {
            string old = g_lcsc[g];
            if (param_pick(g, need)) {
                g_take_pk(g);
                g_src[g] = "по номиналу";
                add_warn(g, attn() + Lf("в атрибуте {0} — заменён на {1} по номиналу", "attribute {0} — replaced with {1} by value", bad, g_lcsc[g], ""));
                if (pk_stock < need) add_warn(g, Lf("склад {0} < нужно {1}", "stock {0} < needed {1}", istr(pk_stock), istr(need), ""));
                return;
            }
            add_warn(g, attn() + Lf("{0}; по номиналу замена не найдена, оставлен {1}", "{0}; no replacement by value, kept {1}", bad, old, ""));
        } else if (bad != "") {
            add_warn(g, attn() + bad);
        }
        if (vstock < need) add_warn(g, Lf("склад {0} < нужно {1}", "stock {0} < needed {1}", istr(vstock), istr(need), ""));
        return;
    }

    if (!opt_online) {
        g_src[g] = "-";
        return;
    }

    if (param) {
        found = param_pick(g, need);
        if (found) g_src[g] = "по номиналу";
    }

    if (!found) {
        int i, n_valc = 0;
        // у пассива по номиналу номер изготовителя берём только из атрибута
        if (param) build_cands("", g_mpn[g]);
        else build_cands(g_value[g], g_mpn[g]);
        for (i = 0; i < n_cand; i++)
            if (!cand_attr[i]) n_valc++;
        for (i = 0; i < n_cand && !found; i++) {
            int m = pick_mpn(cand[i], need);
            if (!m) continue;
            // номинал сам похож на номер детали, а нашёлся только атрибут MPN —
            // скорее всего атрибут остался от другой детали: только подсказываем
            if (cand_attr[i] && n_valc > 0) {
                add_note(g, Lf("по номиналу не найден; атрибут MPN {0} не подставлен: номинал указывает на другую деталь",
                               "not found by value; MPN attribute {0} not used: the value points to a different part",
                               cand[i] + " = " + pk_code + " (" + pk_model + ")", "", ""));
                break;
            }
            found = 1;
            g_src[g] = "по номеру";
            if (m == 2) {
                g_src[g] = "по началу номера";
                add_note(g, Lf("в каталоге {0} (проверить суффикс)", "catalogue has {0} (check the suffix)", pk_model, "", ""));
            }
            if (cand_attr[i] && squeeze(g_value[g]) != "")
                add_note(g, Lf("номер взят по атрибуту MPN {0}", "part number taken from MPN attribute {0}", cand[i], "", ""));
        }
    }

    if (!found) {
        g_src[g] = "не найден";
        return;
    }
    g_take_pk(g);
    if (pk_stock < need) add_warn(g, Lf("склад {0} < нужно {1}", "stock {0} < needed {1}", istr(pk_stock), istr(need), ""));
}

// fk_finish.ulp — третья фаза: Gerber для JLCPCB, превью слоёв, сборка отчёта и документации
// dmxON FabKit · dmxON by AlexSmith 2026 · см. LICENSE.md
//
// Запускается скриптом второй фазы после MANUFACTURING EXPORT и печати листов для ЛУТ:
//   RUN dmxON_FabKit.ulp -finish <файл состояния>
// Всё, что знала первая фаза, приходит через файл состояния и заготовки HTML во временной папке.

string fn_fbase, fn_disp, fn_out, fn_tmp, fn_base, fn_d1, fn_d2, fn_d3, fn_d4, fn_img, fn_gdir, fn_zip, fn_outline;
int fn_layers = 0;              // слоёв меди по файлам
real fn_minw = 0;               // самая узкая дорожка, мм
int fn_thin = 0;                // штрихов меди тоньше 0.05 мм
string fn_err = "";             // что не получилось (для итогового сообщения)

// ---------------------------------------------------------------- цвета превью

string layer_rgb(string code)
{
    if (code == "GTL") return "#e3a857";
    if (code == "GBL") return "#6f9fe0";
    if (code == "G1") return "#c58fd9";
    if (code == "G2") return "#5fbfaa";
    if (starts_with(code, "G") && isdigit(code[1])) return "#d98f8f";
    if (code == "GTS" || code == "GBS") return "#58b483";
    if (code == "GTP" || code == "GBP") return "#b8bec6";
    if (code == "GTO" || code == "GBO") return "#f1f1ec";
    if (code == "GKO") return "#e8dcc0";
    return "#f0f0f0";
}

// ---------------------------------------------------------------- Gerber

// имя файла для JLCPCB: <плата>.GTL, <плата>.G1, <плата>.XLN; второй файл сверловки — <плата>_XLN1.XLN
// размер файла: байты или КБ
string fsize(int b)
{
    if (b < 1024) return istr(b) + " B";
    return istr((b + 512) / 1024) + " KB";
}

// имя файлов внутри архива: только латиница, цифры и - _ .
string zip_base(string b)
{
    string t = "";
    for (int i = 0; b[i]; i++) {
        int c = b[i];
        if ((c >= 'a' && c <= 'z') || (c >= 'A' && c <= 'Z') || (c >= '0' && c <= '9') || c == '-' || c == '_' || c == '.') t += b[i];
        else if (c < 128) t += "_";
    }
    if (t == "") t = "board";
    return t;
}

// бэкап проекта самим FabKit: схема и плата — те EAGLE 9 файлы, которые Fusion отдаёт ULP (с несохранёнными
// правками и встроенными библиотеками) — архивом в 05_BACKUP пакета
string fn_bk_zip = "";

void backup_design()
{
    string sch = "", brd = "";
    if (board) board(B) {
        brd = B.name;
        project.schematic(S) sch = S.name;
    }
    if (brd == "" || !file_exists(brd)) return;
    string d5 = fn_out + "/05_BACKUP", zt = fn_tmp + "/bk";
    string nm = zip_base(fn_fbase);
    string zn = nm + "_backup_" + t2string(time(), "yyyy-MM-dd_hhmm") + ".zip";
    output(fn_tmp + "/bk_restore.txt", "wt") {
        printf("dmxON FabKit - design backup / kopia projektu / Sicherung / copia del diseno\n\n");
        printf("%s.sch, %s.brd - EAGLE 9 schematic and board as exported by Fusion at %s,\n", nm, nm, t2string(time(), "yyyy-MM-dd hh:mm"));
        printf("including unsaved changes and the embedded libraries.\n\n");
        printf("Restore: Fusion -> Data panel -> Upload -> both files (or File -> Open in EAGLE 9);\n");
        printf("the board and schematic open as one Electronics design.\n");
    }
    string files = " " + nm + ".brd RESTORE.txt";
    string cmd = "mkdir " + qp(zt) + " 2>nul & mkdir " + qp(d5) + " 2>nul & copy /y " + qp(brd) + " " + qp(zt + "/" + nm + ".brd") + " >nul";
    if (sch != "" && file_exists(sch)) {
        cmd += " & copy /y " + qp(sch) + " " + qp(zt + "/" + nm + ".sch") + " >nul";
        files += " " + nm + ".sch";
    }
    cmd += " & copy /y " + qp(fn_tmp + "/bk_restore.txt") + " " + qp(zt + "/RESTORE.txt") + " >nul";
    cmd += " & cd /d " + qp(zt) + " && tar -a -cf ..\\bk.zip" + files + " && copy /y ..\\bk.zip " + qp(d5 + "/" + zn) + " >nul";
    shell(cmd);
    if (file_exists(d5 + "/" + zn)) fn_bk_zip = "05_BACKUP/" + zn;
}

string gf_jlc_name(int i)
{
    if (gf_code[i] != "XLN" && starts_with(gf_code[i], "XLN")) return fn_fbase + "_" + gf_code[i] + ".XLN";
    return fn_fbase + "." + gf_code[i];
}

int gf_ord[];
int gs_ap_[], gs_d01_[], gs_d03_[], gs_reg_[];
real gs_minw_[], gs_over_[];      // gs_over_ — насколько слой выходит за контур платы, мм

void finish_gerber()
{
    int i;
    string cam = fn_tmp + "/cam";
    if (!file_exists(fn_tmp + "/cam.zip")) {
        fn_err += "MANUFACTURING EXPORT: cam.zip not found. ";
        n_gf = 0;
        return;
    }
    fk_log("Gerber: unpack");
    // tar.exe не понимает кириллицу в аргументах: переходим в папку и даём ему относительные имена
    shell("mkdir " + qp(cam) + " 2>nul & cd /d " + qp(cam) + " && tar -xf ..\\cam.zip");
    shell("dir /s /b /a-d " + qp(cam) + " > " + qp(fn_tmp + "/cam_list.txt"));
    gerber_classify(fn_tmp + "/cam_list.txt");
    if (n_gf == 0) { fn_err += "Gerber: no layer files in the export. "; return; }

    // порядок: контур, верх ... низ, сверловка
    numeric string ok[];
    for (i = 0; i < n_gf; i++) { string t; sprintf(t, "%03d", gf_order[i]); ok[i] = t; }
    sort(n_gf, gf_ord, ok);

    // имена JLCPCB и архив
    fn_gdir = fn_d1 + "/JLCPCB_GERBER";
    string ud = fn_gdir + "/unpacked";
    shell("mkdir " + qp(ud) + " 2>nul");
    // архив собирается во временной папке из копий с латинскими именами (tar и кириллица несовместимы),
    // затем копируется на место; JLCPCB узнаёт слой по расширению
    string zb = zip_base(fn_fbase);
    string zt = fn_tmp + "/jlc";
    shell("mkdir " + qp(zt) + " 2>nul");
    string cmd = "", names = "";
    for (i = 0; i < n_gf; i++) {
        gf_dst[i] = gf_jlc_name(i);
        string zn = zb + strsub(gf_dst[i], strlen(fn_fbase));
        if (cmd != "") cmd += " & ";
        cmd += "copy /y " + qp(gf_src[i]) + " " + qp(ud + "/" + gf_dst[i]) + " >nul & copy /y " + qp(gf_src[i]) + " " + qp(zt + "/" + zn) + " >nul";
        if (strlen(cmd) > 5000) { shell(cmd); cmd = ""; }
        names += " \"" + zn + "\"";
    }
    if (cmd != "") shell(cmd);
    fn_zip = fn_gdir + "/" + fn_fbase + "_Gerber_JLCPCB.zip";
    shell("cd /d " + qp(zt) + " && tar -a -cf ..\\gerber.zip" + names + " && copy /y ..\\gerber.zip " + qp(fn_zip) + " >nul");
    for (i = 0; i < n_gf; i++) gf_size[i] = filesize(ud + "/" + gf_dst[i]);
    if (!file_exists(fn_zip)) fn_err += "Gerber: zip not created. ";

    // превью слоёв
    fn_img = fn_d2 + "/img";
    shell("mkdir " + qp(fn_img) + " 2>nul");
    vb_set(strtod(st_get("bx1")), strtod(st_get("by1")), strtod(st_get("bx2")), strtod(st_get("by2")));
    fn_layers = 0; fn_minw = 0; fn_thin = 0;
    for (i = 0; i < n_gf; i++) {
        string code = gf_code[i];
        fk_log("Gerber: " + code);
        if (starts_with(code, "XLN")) {
            excellon_parse(gf_src[i]);
            write_drill_svg(fn_img + "/L_" + code + ".svg", "#e9e4d6", "#9aa3ab");
            gs_ap_[i] = n_tool; gs_d01_[i] = 0; gs_d03_[i] = n_hole; gs_reg_[i] = n_slot; gs_minw_[i] = drill_min();
            continue;
        }
        // превью слоя без масок, на тёмном фоне: годится и для PDF
        write_flat_svg(gf_src[i], fn_img + "/L_" + code + ".svg", layer_rgb(code), "#12171c");
        gs_ap_[i] = gs_ap; gs_d01_[i] = gs_d01; gs_d03_[i] = gs_d03; gs_reg_[i] = gs_reg; gs_minw_[i] = gs_minw;
        gs_over_[i] = 0;
        if (gs_eset) {
            real bx1 = strtod(st_get("bx1")), by1 = strtod(st_get("by1")), bx2 = strtod(st_get("bx2")), by2 = strtod(st_get("by2"));
            gs_over_[i] = max(max(bx1 - gs_ex1, gs_ex2 - bx2), max(by1 - gs_ey1, gs_ey2 - by2));
            if (gs_over_[i] < 0) gs_over_[i] = 0;
        }
        if (code == "GTL" || code == "GBL" || (starts_with(code, "G") && isdigit(code[1]))) {
            fn_layers++;
            if (gs_minw > 0 && (fn_minw == 0 || gs_minw < fn_minw)) fn_minw = gs_minw;
            fn_thin += gs_thin;
        }
    }
    // сверловка нужна и для вида платы
    int dx = gf_find("XLN");
    if (dx >= 0) excellon_parse(gf_src[dx]);

    // вид платы «как изготовят»: основа, медь, маска, покрытие, шелкография, отверстия
    string outline = "";
    if (file_exists(fn_outline)) fileread(outline, fn_outline);
    outline = trim(outline);
    string mc = mask_rgb(opt_mask), sc = silk_rgb(opt_silk), fc = finish_rgb(opt_finish);
    for (int side = 0; side < 2; side++) {
        string pre = "top", cu = "GTL", mk = "GTS", sk = "GTO";
        if (side) { pre = "bot"; cu = "GBL"; mk = "GBS"; sk = "GBO"; }
        int ic = gf_find(cu), im = gf_find(mk), is = gf_find(sk);
        fk_log("render " + pre);
        write_substrate_svg(fn_img + "/" + pre + "_1_base.svg", outline, "#b9a46a");
        if (ic >= 0) write_layer_svg(gf_src[ic], fn_img + "/" + pre + "_2_cu.svg", "#c98b3c");
        if (im >= 0) write_mask_svg(gf_src[im], fn_img + "/" + pre + "_3_mask.svg", outline, mc);
        if (ic >= 0 && im >= 0) write_finish_svg(gf_src[ic], gf_src[im], fn_img + "/" + pre + "_4_fin.svg", fc);
        string msrc = "";
        if (im >= 0) msrc = gf_src[im];
        if (is >= 0) write_silk_svg(gf_src[is], msrc, outline, fn_img + "/" + pre + "_5_silk.svg", sc);
        // тот же вид одним рисунком без масок — для PDF и стартовой страницы
        string fcu = "", fmk = "", fsk = "";
        if (ic >= 0) fcu = gf_src[ic];
        if (im >= 0) fmk = gf_src[im];
        if (is >= 0) fsk = gf_src[is];
        write_composite_svg(fn_img + "/" + pre + "_flat.svg", fcu, fmk, fsk, outline, mc, sc, fc, "");
    }
    write_drill_svg(fn_img + "/drill_holes.svg", "#0d1014", "#0d1014");
}

// слои вида платы для стороны: список картинок по порядку
string RENDER_PARTS[] = { "_1_base", "_2_cu", "_3_mask", "_4_fin", "_5_silk" };

string render_imgs(string pre, string rel)
{
    string s = "";
    for (int k = 0; k < 5; k++) {
        string f = pre + RENDER_PARTS[k] + ".svg";
        if (file_exists(fn_img + "/" + f)) s += "<img src=\"" + rel + f + "\" alt=\"\">";
    }
    if (file_exists(fn_img + "/drill_holes.svg")) s += "<img src=\"" + rel + "drill_holes.svg\" alt=\"\">";
    return s;
}

// ---------------------------------------------------------------- параметры заказа

real JLC_THICK[] = { 0.4, 0.6, 0.8, 1.0, 1.2, 1.6, 2.0 };

string thick_jlc()
{
    string t = trim(opt_thick);
    real v = 0;
    if (t == "" || strupr(t) == "AUTO") v = strtod(job_val("BoardThickness"));
    else v = strtod(t);
    if (v <= 0) v = 1.6;
    real best = 1.6, bd = 100;
    for (int i = 0; i < 7; i++) {
        real d = abs(JLC_THICK[i] - v);
        if (d < bd) { bd = d; best = JLC_THICK[i]; }
    }
    return num(best);
}

string board_size_txt()
{
    real w = strtod(st_get("bx2")) - strtod(st_get("bx1")), hh = strtod(st_get("by2")) - strtod(st_get("by1"));
    return num(round(w * 100) / 100.0) + " × " + num(round(hh * 100) / 100.0);
}

string assembly_side()
{
    if (st_geti("n_bot") > 0 && st_geti("n_top") > 0) return "Both sides";
    if (st_geti("n_bot") > 0) return "Bottom side";
    return "Top side";
}

string par_row(string ru, string en, string val)
{
    return "<tr><td>" + h(L(ru, en)) + "</td><td><b>" + h(val) + "</b></td></tr>";
}

// проверка технологичности против возможностей JLCPCB: строки «класс|текст»
string dfm_items[];
int n_dfm = 0;

void dfm_add(string cls, string txt)
{
    dfm_items[n_dfm++] = cls + "|" + txt;
}

void dfm_check()
{
    n_dfm = 0;
    // одна версия на всё: имена файлов, штампы и надпись на плате
    string sv = st_get("silk_ver"), dr = st_get("design_rev");
    if (dr != "" && dr != rev_norm(tb_rev) && !st_geti("rev_written"))
        dfm_add("warn", Lf("в проекте атрибут REV = {0}, а пакет — версии {1}: запустите FabKit из окна, он запишет версию в проект",
                           "the design attribute REV is {0}, the package is version {1}: run FabKit from its dialog to save the version in the design", dr, rev_norm(tb_rev), ""));
    if (sv != "" && sv != rev_norm(tb_rev))
        dfm_add("warn", Lf("на плате написана версия {0}, а пакет — версии {1}", "the board text says version {0}, the package is version {1}", sv, rev_norm(tb_rev), ""));
    else
        dfm_add("ok", Lf("версия {0} — в именах файлов, штампах{1}", "version {0} — in file names and title blocks{1}", rev_norm(tb_rev),
                         sv != "" ? L(" и на плате", " and on the board") : "", ""));
    real tmin = 0.10;                       // 1–2 слоя: 0.10 мм (4 mil), многослойные: 0.09 мм
    if (fn_layers >= 4) tmin = 0.09;
    if (fn_minw > 0) {
        string w = num(round(fn_minw * 1000) / 1000.0);
        if (fn_minw >= 0.127) dfm_add("ok", Lf("ширина линий от {0} мм — стандарт", "track width from {0} mm — standard", w, "", ""));
        else if (fn_minw >= tmin) dfm_add("warn", Lf("ширина линий от {0} мм — на пределе возможностей", "track width from {0} mm — at the capability limit", w, "", ""));
        else dfm_add("bad", Lf("ширина линий {0} мм меньше допустимой {1} мм", "track width {0} mm is below the {1} mm minimum", w, num(tmin), ""));
    }
    if (fn_thin > 0)
        dfm_add("warn", Lf("штрихов меди тоньше 0.05 мм (графика, логотип): {0} — изготовлены не будут",
                           "{0} copper strokes thinner than 0.05 mm (artwork, logo) will not be reproduced", istr(fn_thin), "", ""));
    // слои за контуром платы: медь — ошибка, остальное изготовитель обрежет
    for (int gi = 0; gi < n_gf; gi++) {
        string c = gf_code[gi];
        if (starts_with(c, "XLN") || c == "GKO" || gs_over_[gi] <= 0.3) continue;
        string ov = num(round(gs_over_[gi] * 10) / 10.0);
        if (c == "GTL" || c == "GBL" || (starts_with(c, "G") && isdigit(c[1])))
            dfm_add("bad", gf_name[gi] + ": " + Lf("медь выходит за контур платы на {0} мм", "copper extends {0} mm beyond the board outline", ov, "", ""));
        else
            dfm_add("warn", gf_name[gi] + ": " + Lf("выходит за контур на {0} мм — изготовитель обрежет", "extends {0} mm beyond the outline — the fab will clip it", ov, "", ""));
    }
    if (n_tool > 0) {
        real dm = drill_min();
        string d = num(dm);
        if (dm >= 0.3) dfm_add("ok", Lf("мин. отверстие {0} мм — стандарт", "min hole {0} mm — standard", d, "", ""));
        else if (dm >= 0.15 && fn_layers >= 4) dfm_add("warn", Lf("мин. отверстие {0} мм: допустимо для многослойных, отверстия меньше 0.3 мм могут увеличить цену",
                                                                  "min hole {0} mm: fine for multilayer, holes below 0.3 mm may raise the price", d, "", ""));
        else dfm_add("bad", Lf("мин. отверстие {0} мм меньше стандартных 0.3 мм для 1–2 слоёв", "min hole {0} mm is below the standard 0.3 mm for 1–2 layers", d, "", ""));
    }
}

string dfm_html()
{
    string s = "";
    for (int i = 0; i < n_dfm; i++) {
        int bar = strstr(dfm_items[i], "|");
        string cls = strsub(dfm_items[i], 0, bar), txt = strsub(dfm_items[i], bar + 1);
        string pc = "p-ok", mk = "OK";
        if (cls == "warn") { pc = "p-warn"; mk = "!"; }
        if (cls == "bad") { pc = "p-bad"; mk = "&times;"; }
        s += "<div style=\"margin:4px 0\"><span class=\"pill " + pc + "\">" + mk + "</span> " + h(txt) + "</div>";
    }
    return s;
}

string order_params()
{
    string s = "<table>";
    s += par_row("Материал", "Base material", "FR-4");
    s += par_row("Слоёв", "Layers", istr(fn_layers));
    s += par_row("Размер, мм", "Dimensions, mm", board_size_txt());
    s += par_row("Количество плат", "PCB qty", istr(opt_boards));
    s += par_row("Толщина, мм", "PCB thickness, mm", thick_jlc());
    s += par_row("Цвет маски", "Solder mask colour", opt_mask);
    s += par_row("Цвет шелкографии", "Silkscreen", opt_silk);
    s += par_row("Покрытие", "Surface finish", opt_finish);
    s += par_row("Медь снаружи", "Outer copper weight", "1 oz");
    if (fn_minw > 0) s += par_row("Мин. ширина линии, мм", "Min track width, mm", num(round(fn_minw * 1000) / 1000.0));
    if (n_tool > 0) s += par_row("Мин. отверстие, мм", "Min hole size, mm", num(drill_min()));
    s += par_row("Сторона монтажа", "Assembly side", assembly_side());
    s += "</table>";
    return s;
}

// ---------------------------------------------------------------- разделы отчёта третьей фазы

string rel1 = "../01_JLCPCB_ORDER/";

string sec_render()
{
    if (n_gf == 0) return "";
    string s = "<div class=\"boards\">";
    s += "<figure class=\"pcb\"><div class=\"scene\"><div class=\"stack\">" + render_imgs("top", "img/") + "</div></div>" +
         "<figcaption>" + h(L("Верх", "Top")) + "</figcaption></figure>";
    if (gf_find("GBL") >= 0)
        s += "<figure class=\"pcb bot\"><div class=\"scene\"><div class=\"stack\">" + render_imgs("bot", "img/") + "</div></div>" +
             "<figcaption>" + h(L("Низ (вид снизу)", "Bottom (as seen from below)")) + "</figcaption></figure>";
    s += "</div><p class=\"hint\">" + h(L("Наведите курсор — слои раздвинутся", "Hover to explode the layer stack")) + "</p>";
    return s;
}

string file_link(string rel, string name, string label)
{
    return "<a href=\"" + replace_all(rel + name, " ", "%20") + "\">" + h(label) + "</a>";
}

string sec_order()
{
    string bom = fn_fbase + "_JLCPCB_BOM.csv", cpl = fn_fbase + "_JLCPCB_CPL.csv";
    string s = h2s("order", "Заказ на JLCPCB", "Ordering at JLCPCB");
    s += "<div class=\"grid2\"><div class=\"box\">";
    s += "<h3 style=\"margin-top:0\">" + hl("Что загрузить", "What to upload") + "</h3><ol style=\"margin:0;padding-left:20px\">";
    if (n_gf > 0)
        s += "<li>" + hs("Плата: архив", "PCB: archive") + " " + file_link(rel1 + "JLCPCB_GERBER/", fn_fbase + "_Gerber_JLCPCB.zip", fn_fbase + "_Gerber_JLCPCB.zip") +
             " → jlcpcb.com/quote → Add gerber file</li>";
    s += "<li>" + hs("Сборка (PCB Assembly): BOM", "Assembly: BOM") + " " + file_link(rel1, bom, bom) + "</li>";
    s += "<li>" + hs("и CPL (координаты)", "and CPL (pick & place)") + " " + file_link(rel1, cpl, cpl) + "</li>";
    s += "<li>" + hs("В предпросмотре JLCPCB проверить поворот деталей из раздела «Внимание».",
                     "In the JLCPCB preview check rotation of parts listed under Attention.") + "</li>";
    s += "</ol>";
    if (n_dfm > 0) s += "<h3>" + hl("Проверка технологичности", "Manufacturability check") + "</h3>" + dfm_html();
    s += "</div><div class=\"box\"><h3 style=\"margin-top:0\">" + hl("Параметры платы для формы заказа", "PCB parameters for the order form") + "</h3>";
    s += order_params() + "</div></div>";
    s += sec_end();
    return s;
}

string sec_gerber()
{
    if (n_gf == 0) {
        return h2s("gerber", "Gerber", "Gerber") + "<p class=\"note\">" + h(L("Gerber не выгружен", "Gerber was not exported") + ": " + fn_err) + "</p>" + sec_end();
    }
    int i, k;
    string s = h2s("gerber", "Слои Gerber и сверловка", "Gerber layers and drilling");
    s += lead("Файлы названы так, как их ждёт JLCPCB (Protel: GTL, GBL, G1…, GTS, GTP, GTO, GKO, XLN). Включайте и выключайте слои слева.",
              "Files are named the way JLCPCB expects (Protel: GTL, GBL, G1…, GTS, GTP, GTO, GKO, XLN). Toggle layers on the left.");
    // переключатели слоёв (без скриптов: флажки + CSS)
    string css = "<style>", ctl = "", inp = "", stg = "";
    int first = 1;
    // сцена снизу вверх: нижние слои, внутренние, верхние, затем контур и отверстия поверх всего
    int st_ord[], n_so = 0;
    for (k = n_gf - 1; k >= 0; k--) {
        i = gf_ord[k];
        if (gf_code[i] != "GKO" && !starts_with(gf_code[i], "XLN")) st_ord[n_so++] = i;
    }
    for (k = 0; k < n_gf; k++) if (gf_code[gf_ord[k]] == "GKO") st_ord[n_so++] = gf_ord[k];
    for (k = 0; k < n_gf; k++) if (starts_with(gf_code[gf_ord[k]], "XLN")) st_ord[n_so++] = gf_ord[k];
    for (k = 0; k < n_so; k++) {
        i = st_ord[k];
        string id = "ly" + istr(k);
        int on = (gf_code[i] == "GKO" || gf_code[i] == "GTL" || gf_code[i] == "GTO" || gf_code[i] == "XLN");
        inp += "<input type=\"checkbox\" id=\"" + id + "\"";
        if (on) inp += " checked";
        inp += ">";
        css += "#" + id + ":not(:checked)~.lv-stage .i" + id + "{opacity:0}#" + id + ":not(:checked)~.lv-ctl label[for=" + id + "]{opacity:.45}";
        // список переключателей — сверху вниз, как слои лежат на плате
        ctl = "<label for=\"" + id + "\"><i style=\"background:" + layer_rgb(gf_code[i]) + "\"></i><b>" + gf_code[i] + "</b><span>" +
              h(gf_name[i]) + "</span></label>" + ctl;
        string cls = "i" + id;
        if (first) { cls += " base"; first = 0; }
        stg += "<img class=\"" + cls + "\" src=\"img/L_" + gf_code[i] + ".svg\" alt=\"" + gf_code[i] + "\">";
    }
    css += "</style>";
    s += css + "<div class=\"lv\">" + inp + "<div class=\"lv-ctl\">" + ctl + "</div><div class=\"lv-stage\"><div class=\"lv-in\">" + stg + "</div></div></div>";

    // галерея слоёв
    s += "<h3>" + hl("Все слои по отдельности", "Every layer on its own") + "</h3><div class=\"gal\">";
    for (k = 0; k < n_gf; k++) {
        i = gf_ord[k];
        string st;
        if (starts_with(gf_code[i], "XLN")) st = Lf("инструментов: {0} · отверстий: {1}", "{0} tools · {1} holes", istr(gs_ap_[i]), istr(gs_d03_[i]), "");
        else st = Lf("апертур: {0} · линий: {1} · вспышек: {2}", "{0} apertures · {1} lines · {2} flashes", istr(gs_ap_[i]), istr(gs_d01_[i]), istr(gs_d03_[i])) +
                  " · " + Lf("областей: {0}", "{0} regions", istr(gs_reg_[i]), "", "");
        s += "<div class=\"lay\"><div class=\"th\"><img src=\"img/L_" + gf_code[i] + ".svg\" alt=\"\" loading=\"lazy\"></div><div class=\"tx\"><b>" +
             gf_code[i] + "</b>" + h(gf_name[i]) + "<br><span class=\"small\">" + h(gf_dst[i]) +
             " · " + fsize(gf_size[i]) + " · " + h(st) + "</span></div></div>";
    }
    s += "</div>";

    // сверловка
    int dx = gf_find("XLN");
    if (dx >= 0) {
        excellon_parse(gf_src[dx]);
        s += "<h3>" + hl("Сверловка", "Drilling") + "</h3><div class=\"grid2\"><div class=\"tw\"><table><thead><tr>" +
             th2("Инструмент", "Tool") + th2n("Диаметр, мм", "Diameter, mm") + th2n("Отверстий", "Holes") + "</tr></thead><tbody>";
        for (k = 0; k < n_tool; k++) {
            string r;
            sprintf(r, "<tr><td>T%02d</td><td class=\"num\">%.3f</td><td class=\"num\">%d</td></tr>", tl_no[k], tl_d[k], tl_hits[k]);
            s += r;
        }
        string tot;
        sprintf(tot, "<tr><td><b>%s</b></td><td class=\"num\">min %.3f</td><td class=\"num\"><b>%d</b></td></tr>", h(L("Итого", "Total")), drill_min(), n_hole);
        s += tot + "</tbody></table></div>";
        s += "<div class=\"lay\"><div class=\"th\"><img src=\"img/L_XLN.svg\" alt=\"\" style=\"background:#12171c\"></div><div class=\"tx\">" +
             hs("Карта отверстий", "Drill map") + "</div></div></div>";
    }

    // файлы
    s += "<h3>" + hl("Файлы для JLCPCB", "Files for JLCPCB") + "</h3><div class=\"tw\"><table><thead><tr>" + th2("Файл", "File") +
         th2("Слой", "Layer") + th2("Исходный файл Fusion", "Fusion source") + th2n("Размер", "Size") + "</tr></thead><tbody>";
    for (k = 0; k < n_gf; k++) {
        i = gf_ord[k];
        s += "<tr><td><code>" + h(gf_dst[i]) + "</code></td><td>" + h(gf_name[i]) + "</td><td class=\"small\">" +
             h(filename(gf_src[i])) + "</td><td class=\"num\">" + fsize(gf_size[i]) + "</td></tr>";
    }
    s += "</tbody></table></div>";
    s += sec_end();
    return s;
}

// ---------------------------------------------------------------- чертёж печатной платы (третья фаза)

// класс точности по ГОСТ Р 53429-2009 по наименьшей ширине проводника (таблица 1: 0,75 … 0,05 мм)
int gost_class(real w)
{
    real t[] = { 0.75, 0.45, 0.25, 0.15, 0.10, 0.075, 0.05 };
    if (w <= 0) return 4;
    for (int i = 0; i < 7; i++) if (w >= t[i] - 0.0005) return i + 1;
    return 7;
}

string color_txt(string c)
{
    if (c == "Green") return L("зелёный", "green");
    if (c == "Purple") return L("фиолетовый", "purple");
    if (c == "Red") return L("красный", "red");
    if (c == "Yellow") return L("жёлтый", "yellow");
    if (c == "Blue") return L("синий", "blue");
    if (c == "White") return L("белый", "white");
    if (c == "Black") return L("чёрный", "black");
    return c;
}

string finish_txt(string f)
{
    if (f == "HASL (with lead)") return L("горячее лужение HASL (Sn-Pb)", "HASL (tin-lead)");
    if (f == "LeadFree HASL") return L("горячее лужение HASL без свинца", "lead-free HASL");
    if (f == "ENIG") return L("иммерсионное золото ENIG по IPC-4552B", "ENIG per IPC-4552B");
    if (f == "OSP") return L("органическое покрытие OSP", "OSP (organic solderability preservative)");
    return f;
}

// технические требования к плате
string fab_notes()
{
    string c = istr(dc_class);
    real th = strtod(thick_jlc());
    string s = "";
    if (doc_std == 1)
        s += Lf("Плату изготовить по ГОСТ Р 53429-2009, класс точности {0}; требования к качеству — по IPC-6012F, класс {1}; приёмка — по IPC-A-600M.",
                "Fabricate per GOST R 53429-2009, accuracy class {0}; quality per IPC-6012F, Class {1}; acceptance per IPC-A-600M.",
                istr(gost_class(fn_minw)), c, "") + "\n";
    else
        s += Lf("Изготовить по IPC-6012F, класс {0}; приёмка — по IPC-A-600M, класс {0}.",
                "Fabricate per IPC-6012F, Class {0}; acceptability per IPC-A-600M, Class {0}.", c, "", "") + "\n";
    s += Lf("Материал основания — стеклотекстолит FR-4 по IPC-4101F/21; толщина платы {0} мм ±10 %.",
            "Base material: FR-4 per IPC-4101F/21; board thickness {0} mm ±10 %.", dnum(th), "", "") + "\n";
    s += Lf("Слоёв меди: {0}; толщина наружной меди 35 мкм (1 oz) после металлизации; структура слоёв — по таблице.",
            "Copper layers: {0}; outer copper 35 µm (1 oz) finished; layer structure per table.", istr(fn_layers), "", "") + "\n";
    s += Lf("Паяльная маска — жидкая фотопроявляемая по IPC-SM-840E, класс T, цвет {0}, с двух сторон; маркировка — непроводящей краской, цвет {1}.",
            "Solder mask: LPI per IPC-SM-840E, Class T, {0}, both sides; legend in non-conductive ink, {1}.",
            color_txt(opt_mask), color_txt(opt_silk), "") + "\n";
    s += Lf("Финишное покрытие: {0}; паяемость — по J-STD-003D.", "Surface finish: {0}; solderability per J-STD-003D.", finish_txt(opt_finish), "", "") + "\n";
    s += L("Электрический контроль всех цепей (100 %) — по IPC-9252B.", "100 % electrical test of all nets per IPC-9252B.") + "\n";
    if (fn_minw > 0 && n_tool > 0)
        s += Lf("Наименьшая ширина проводника {0} мм; наименьший диаметр отверстия {1} мм.",
                "Minimum conductor width {0} mm; minimum finished hole {1} mm.", dnum(round(fn_minw * 1000) / 1000.0), dnum(drill_min()), "") + "\n";
    s += Lf("Рисунок проводников — по файлам Gerber {0} (RS-274X), координаты отверстий — по файлу Excellon.",
            "Conductive pattern per Gerber data {0} (RS-274X); hole positions per the Excellon file.", fn_fbase + "_Gerber_JLCPCB.zip", "", "") + "\n";
    s += Lf("Предельные отклонения размеров контура ±{0} мм; размеры — в миллиметрах.",
            "Outline tolerance ±{0} mm; dimensions in millimetres.", dnum(0.2), "", "") + "\n";
    s += Lf("Коробление и скручивание — не более {0} % (плата с поверхностным монтажом).",
            "Bow and twist max {0} % (board with surface-mount parts).", dnum(0.75), "", "") + "\n";
    if (opt_finish != "HASL (with lead)")
        s += L("Плата — без свинца, по директиве RoHS 2011/65/EU.", "Lead-free, RoHS compliant (Directive 2011/65/EU).") + "\n";
    return s;
}

// вид платы с отверстиями и габаритными размерами (ISO 129-1): масштаб — в fv_sc
real fv_sc = 1;

string fab_view(real aw, real ah)
{
    real bx1 = strtod(st_get("bx1")), by1 = strtod(st_get("by1")), bx2 = strtod(st_get("bx2")), by2 = strtod(st_get("by2"));
    real bw = bx2 - bx1, bh = by2 - by1;
    real sc = pick_scale(bw, bh, aw - 18, ah - 18);
    fv_sc = sc;
    real m = 3 / sc, md = 16 / sc;
    real W = bw + m + md, H = bh + m + md;
    string s, t;
    sprintf(s, "<svg class=\"dimv\" viewBox=\"0 0 %s %s\" style=\"width:%smm;height:%smm\" xmlns=\"http://www.w3.org/2000/svg\">",
            f3(W), f3(H), f3(W * sc), f3(H * sc));
    string outline = "";
    if (file_exists(fn_outline)) fileread(outline, fn_outline);
    outline = trim(outline);
    string tr;
    sprintf(tr, "matrix(1 0 0 -1 %s %s)", f3(m - bx1), f3(by2 + m));
    if (outline != "")
        s += "<path transform=\"" + tr + "\" d=\"" + outline + "\" fill=\"none\" stroke=\"#000\" stroke-width=\"" + f3(0.5 / sc) + "\"/>";
    else {
        sprintf(t, "<rect x=\"%s\" y=\"%s\" width=\"%s\" height=\"%s\" fill=\"none\" stroke=\"#000\" stroke-width=\"%s\"/>", f3(m), f3(m), f3(bw), f3(bh), f3(0.5 / sc));
        s += t;
    }
    // отверстия из файла сверловки
    s += "<g transform=\"" + tr + "\" fill=\"none\" stroke=\"#000\" stroke-width=\"" + f3(0.18 / sc) + "\">";
    for (int i = 0; i < n_hole; i++) {
        sprintf(t, "<circle cx=\"%s\" cy=\"%s\" r=\"%s\"/>", f4(hl_x[i]), f4(hl_y[i]), f4(hl_d[i] / 2));
        s += t;
    }
    s += "</g>";
    // размеры: тонкие линии 0,25 мм, стрелки 3 мм, текст 3,5 мм над размерной линией
    real lw = 0.25 / sc, al = 3 / sc, aw2 = 0.5 / sc, fs = 3.5 / 0.72 / sc;
    real yd = m + bh + 9 / sc, xd = m + bw + 9 / sc;
    sprintf(t, "<g stroke=\"#000\" stroke-width=\"%s\">", f3(lw));
    s += t;
    sprintf(t, "<line x1=\"%s\" y1=\"%s\" x2=\"%s\" y2=\"%s\"/><line x1=\"%s\" y1=\"%s\" x2=\"%s\" y2=\"%s\"/><line x1=\"%s\" y1=\"%s\" x2=\"%s\" y2=\"%s\"/>",
            f3(m), f3(m + bh + 1 / sc), f3(m), f3(yd + 2 / sc), f3(m + bw), f3(m + bh + 1 / sc), f3(m + bw), f3(yd + 2 / sc),
            f3(m), f3(yd), f3(m + bw), f3(yd));
    s += t;
    sprintf(t, "<line x1=\"%s\" y1=\"%s\" x2=\"%s\" y2=\"%s\"/><line x1=\"%s\" y1=\"%s\" x2=\"%s\" y2=\"%s\"/><line x1=\"%s\" y1=\"%s\" x2=\"%s\" y2=\"%s\"/>",
            f3(m + bw + 1 / sc), f3(m), f3(xd + 2 / sc), f3(m), f3(m + bw + 1 / sc), f3(m + bh), f3(xd + 2 / sc), f3(m + bh),
            f3(xd), f3(m), f3(xd), f3(m + bh));
    s += t;
    s += "</g><g fill=\"#000\">";
    sprintf(t, "<path d=\"M%s %sl%s %sv%sz M%s %sl%s %sv%sz M%s %sl%s %sh%sz M%s %sl%s %sh%sz\"/>",
            f3(m), f3(yd), f3(al), f3(-aw2), f3(2 * aw2),
            f3(m + bw), f3(yd), f3(-al), f3(-aw2), f3(2 * aw2),
            f3(xd), f3(m), f3(-aw2), f3(al), f3(2 * aw2),
            f3(xd), f3(m + bh), f3(-aw2), f3(-al), f3(2 * aw2));
    s += t;
    sprintf(t, "<text x=\"%s\" y=\"%s\" font-size=\"%s\" text-anchor=\"middle\">%s</text>", f3(m + bw / 2), f3(yd - 1 / sc), f3(fs), dnum(round(bw * 100) / 100.0));
    s += t;
    sprintf(t, "<text x=\"%s\" y=\"%s\" font-size=\"%s\" text-anchor=\"middle\" transform=\"rotate(-90 %s %s)\">%s</text>",
            f3(xd - 1 / sc), f3(m + bh / 2), f3(fs), f3(xd - 1 / sc), f3(m + bh / 2), dnum(round(bh * 100) / 100.0));
    s += t;
    s += "</g></svg>";
    return s;
}

// таблицы: структура слоёв и сверловка
string fab_tables()
{
    string s = "<div class=\"fx\" style=\"display:flex;gap:4mm;align-items:flex-start\">";
    s += "<table><tr><th></th><th>" + h(L("Слой", "Layer")) + "</th><th>" + h(L("Назначение", "Purpose")) + "</th><th>" + h(L("Файл", "File")) + "</th></tr>";
    for (int k = 0; k < n_gf; k++) {
        int i = gf_ord[k];
        if (starts_with(gf_code[i], "XLN")) continue;
        s += "<tr><td style=\"width:3mm;background:" + layer_rgb(gf_code[i]) + "\"></td><td><b>" + gf_code[i] + "</b></td><td>" + h(gf_name[i]) +
             "</td><td>" + h(gf_dst[i]) + "</td></tr>";
    }
    s += "</table>";
    if (n_tool > 0) {
        s += "<table><tr><th>T</th><th>&Oslash;, " + h(L("мм", "mm")) + "</th><th>" + h(L("Кол.", "Qty")) + "</th></tr>";
        for (int j = 0; j < n_tool; j++)
            s += "<tr><td>T" + (tl_no[j] < 10 ? "0" : "") + istr(tl_no[j]) + "</td><td class=\"n\">" + dnum(round(tl_d[j] * 1000) / 1000.0) +
                 "</td><td class=\"n\">" + istr(tl_hits[j]) + "</td></tr>";
        s += "<tr><td><b>" + h(L("Итого", "Total")) + "</b></td><td></td><td class=\"n\"><b>" + istr(n_hole) + "</b></td></tr></table>";
    }
    return s + "</div>";
}

real fab_tables_h()
{
    int rows = 1;
    for (int k = 0; k < n_gf; k++) if (!starts_with(gf_code[gf_ord[k]], "XLN")) rows++;
    if (n_tool + 2 > rows) rows = n_tool + 2;
    return rows * 4.6 + 2;
}

string fab_doc()
{
    if (n_gf == 0) return "";
    doc_open("FAB", 1);
    string s = sh_open(dc_a3, doc_name("FAB"), "-");
    string nts = fab_notes();
    real nw = sh_aw < 185 ? sh_aw : 185;
    real nh = notes_height(nts, nw), th = fab_tables_h();
    real vh, ty;
    string st;
    if (dc_a3) {
        real band = nh > th ? nh : th;
        vh = sh_ah - band - 6;
        ty = sh_ah - th;
    } else {
        vh = sh_ah - nh - th - 10;
        ty = vh + 4;
    }
    sprintf(st, "left:0;top:0;width:%smm;height:%smm", f3(sh_aw), f3(vh));
    s += "<div class=\"vw\" style=\"" + st + "\">" + fab_view(sh_aw, vh) + "</div>";
    sh_scale = scale_txt(fv_sc);
    sprintf(st, "position:absolute;left:0;top:%smm", f3(ty));
    s += "<div style=\"" + st + "\">" + fab_tables() + "</div>";
    s += "<div class=\"nb\">" + notes_html(nts, nw) + "</div>";
    s += sh_close();
    // слои по отдельности
    int per = dc_a3 ? 8 : 6, cols = dc_a3 ? 4 : 2;
    int pages = (n_gf + per - 1) / per;
    for (int p = 0; p < pages; p++) {
        string tt = L("Слои платы", "PCB layers");
        s += sh_open(dc_a3, tt, "");
        s += "<div class=\"vl\">" + h(tt) + "</div><div class=\"lgrid\" style=\"grid-template-columns:repeat(" + istr(cols) + ",1fr)\">";
        for (int k = p * per; k < (p + 1) * per && k < n_gf; k++) {
            int i = gf_ord[k];
            s += "<div class=\"lcell\"><div class=\"im\"><img src=\"../02_REPORT/img/L_" + gf_code[i] + ".svg\" alt=\"\"></div><div class=\"tx2\"><b>" +
                 gf_code[i] + "</b> " + h(gf_name[i]) + "<br>" + h(gf_dst[i]) + "</div></div>";
        }
        s += "</div>" + sh_close();
    }
    return s;
}

// ---------------------------------------------------------------- перечень документов (ISO)

string DOC_KEYS = "DL|FAB|ASM|PL|SCH|AI|SPEC|PE";

// собранный документ построчно (лист — одна строка)
string dc_al[];
int dc_na = 0;

int count_tok(string s, string tok)
{
    int n = 0, p = 0;
    while (1) {
        int a = strstr(s, tok, p);
        if (a < 0) break;
        n++;
        p = a + strlen(tok);
    }
    return n;
}

// число листов документа: меток {{S:ключ}}
int pages_of(string key)
{
    int n = 0;
    for (int i = 0; i < dc_na; i++) n += count_tok(dc_al[i], "{{S:" + key + "}}");
    return n;
}

string doclist_doc()
{
    doc_open("DL", 1);
    string s = sh_open(0, doc_type("DL"), "");
    real bw = strtod(st_get("bx2")) - strtod(st_get("bx1")), bh = strtod(st_get("by2")) - strtod(st_get("by1"));
    real iw = 110;
    if (bh > 0 && bw * 75 / bh < iw) iw = bw * 75 / bh;
    string st;
    s += "<div class=\"dl\" style=\"padding:2mm 3mm\"><h2>" + h(tb_product) + "</h2><div class=\"sub\">" +
         h(L("Комплект документации для изготовления и сборки печатного узла", "Manufacturing and assembly documentation package")) + "</div>";
    if (n_gf > 0) {
        sprintf(st, "width:%smm", f3(iw));
        s += "<div class=\"rnd\" style=\"" + st + "\"><img src=\"../02_REPORT/img/top_flat.svg\" alt=\"\"></div>";
    }
    s += "<table><tr><th>" + h(L("Плата", "Board")) + "</th><td>" + h(fn_disp) + " · " + h(board_size_txt()) + " " + h(L("мм", "mm")) + "</td></tr>";
    s += "<tr><th>" + h(L("Слоёв меди", "Copper layers")) + "</th><td>" + istr(fn_layers) + "</td></tr>";
    s += "<tr><th>" + h(L("Компонентов", "Components")) + "</th><td>" + istr(st_geti("n_top") + st_geti("n_bot")) + "</td></tr>";
    s += "<tr><th>" + h(L("Плат в партии", "Batch")) + "</th><td>" + istr(opt_boards) + "</td></tr>";
    if (tb_customer != "") s += "<tr><th>" + h(L("Заказчик", "Customer")) + "</th><td>" + h(tb_customer) + "</td></tr>";
    s += "</table>";
    s += "<table><tr><th>№</th><th>" + h(L("Идентификационный номер", "Identification number")) + "</th><th>" + h(L("Вид документа", "Document type")) +
         "</th><th>" + h(L("Листов", "Sheets")) + "</th><th>" + h(L("Формат", "Size")) + "</th></tr>";
    string ks[];
    int nk = strsplit(ks, "DL|FAB|ASM|PL|SCH|AI", '|');
    int no = 0;
    for (int k = 0; k < nk; k++) {
        int np = ks[k] == "DL" ? 1 : pages_of(ks[k]);
        if (np == 0) continue;
        no++;
        string fmt = (ks[k] == "FAB" || ks[k] == "ASM" || ks[k] == "AI") && dc_a3 ? "A3" : "A4";
        if (ks[k] == "SCH") fmt = h(st_get("sch_fmt"));
        s += "<tr><td>" + istr(no) + "</td><td>" + h(doc_id(ks[k])) + "</td><td>" + h(doc_type(ks[k])) + "</td><td>" + istr(np) + "</td><td>" + fmt + "</td></tr>";
    }
    s += "</table><div class=\"sub\">" + h(Lf("Подготовлено: {0}", "Prepared with: {0}", fk_title(), "", "")) + "</div></div>";
    s += sh_close();
    return s;
}

// ---------------------------------------------------------------- сборка файлов из заготовок

// копирует заготовку, заменяя строки-метки готовыми разделами
void assemble_report(string src, string dst)
{
    string lines[];
    int n = fileread(lines, src);
    string r_render = asc(sec_render()), r_order = asc(sec_order()), r_gerber = asc(sec_gerber());
    output(dst, "wt") {
        for (int i = 0; i < n; i++) {
            string t = trim(lines[i]);
            if (t == "<!--FK:RENDER-->") printf("%s\n", r_render);
            else if (t == "<!--FK:ORDER-->") printf("%s\n", r_order);
            else if (t == "<!--FK:GERBER-->") printf("%s\n", r_gerber);
            else printf("%s\n", lines[i]);
        }
    }
}

// номера листов: {{S:ключ}} — по порядку внутри документа, {{N:ключ}} — всего листов документа
void number_sheets()
{
    string ks[];
    int nk = strsplit(ks, DOC_KEYS, '|');
    for (int k = 0; k < nk; k++) {
        int tot = pages_of(ks[k]);
        if (tot == 0) continue;
        string tok = "{{S:" + ks[k] + "}}", ntok = "{{N:" + ks[k] + "}}";
        int no = 0;
        for (int i = 0; i < dc_na; i++) {
            if (strstr(dc_al[i], "{{") < 0) continue;
            dc_al[i] = replace_all(dc_al[i], ntok, istr(tot));
            while (1) {
                int a = strstr(dc_al[i], tok);
                if (a < 0) break;
                no++;
                dc_al[i] = strsub(dc_al[i], 0, a) + istr(no) + strsub(dc_al[i], a + strlen(tok));
            }
        }
    }
}

void assemble_docs(string src, string dst)
{
    string lines[];
    int n = fileread(lines, src);
    dc_date = st_get("date");
    string d_fab = asc(fab_doc());
    string fl[];
    int nf = strsplit(fl, d_fab, '\n');
    int i, k, dl = -1;
    dc_na = 0;
    for (i = 0; i < n; i++) {
        string t = trim(lines[i]);
        if (t == "<!--FK:FAB-->") { for (k = 0; k < nf; k++) if (fl[k] != "") dc_al[dc_na++] = fl[k]; }
        else if (t == "<!--FK:DOCLIST-->") { dl = dc_na; dc_al[dc_na++] = ""; }
        else dc_al[dc_na++] = lines[i];
    }
    if (dl >= 0) dc_al[dl] = replace_all(asc(doclist_doc()), "\n", " ");
    number_sheets();
    output(dst, "wt") for (i = 0; i < dc_na; i++) printf("%s\n", dc_al[i]);
}

// ---------------------------------------------------------------- PDF через Microsoft Edge

string BROWSERS[] = { "C:/Program Files (x86)/Microsoft/Edge/Application/msedge.exe", "C:/Program Files/Microsoft/Edge/Application/msedge.exe",
                      "C:/Program Files/Google/Chrome/Application/chrome.exe", "C:/Program Files (x86)/Google/Chrome/Application/chrome.exe" };

string edge_exe()
{
    for (int i = 0; i < 4; i++)
        if (file_exists(BROWSERS[i])) return BROWSERS[i];
    return "";
}

int html_to_pdf(string html, string pdf)
{
    string ex = edge_exe();
    if (ex == "") { fn_err += "PDF: Microsoft Edge not found. "; return 0; }
    string prof = fn_tmp + "/edge_profile";
    system("\"" + to_win(ex) + "\" --headless=new --disable-gpu --no-first-run --no-default-browser-check --user-data-dir=" + qp(prof) +
           " --no-pdf-header-footer --virtual-time-budget=8000 --print-to-pdf=" + qp(pdf) + " \"" + url_file(html) + "\"");
    // Edge может вернуть управление раньше, чем допишет файл: ждём, пока размер перестанет расти
    wait_file(pdf, 90);
    if (!file_exists(pdf)) { fn_err += "PDF: " + filename(pdf) + " not created. "; return 0; }
    return 1;
}

// ---------------------------------------------------------------- листы ЛУТ из Gerber (1:1)
//
// Листы строятся из тех же Gerber, что уходят на завод: заливки, вырезы и зазоры — как на плате.
// Масштаб задаётся в миллиметрах CSS, Edge печатает его без масштабирования.

// формат бумаги под плату (альбомная): ширина и высота, мм
string tn_paper = "A4";
real tn_pw = 297, tn_ph = 210;

void toner_paper()
{
    tn_paper = "A4"; tn_pw = 297; tn_ph = 210;
    if (vb_w + 20 > tn_pw || vb_h + 36 > tn_ph) { tn_paper = "A3"; tn_pw = 420; tn_ph = 297; }
    if (vb_w + 20 > tn_pw || vb_h + 36 > tn_ph) { tn_paper = "A2"; tn_pw = 594; tn_ph = 420; }
}

// kind: 0 — медь (чёрная, центры отверстий белые), 1 — шелкография, 2 — маска (вскрытия чёрные), 3 — карта сверловки
void toner_sheet(string html, string pdf, int gi, string title, int mirror, int kind)
{
    int ko = gf_find("GKO");
    real x = (tn_pw - vb_w) / 2, y = (tn_ph - vb_h) / 2 + 4;
    string mir = mirror ? L("ЗЕРКАЛЬНО", "MIRRORED") : L("не зеркально", "not mirrored");
    output(html, "wt") {
        printf("<!DOCTYPE html><html lang=\"%s\"><head><meta charset=\"utf-8\"><title>%s</title><style>", LANG_CODE[ui_lang], h(filename(pdf)));
        printf("@page{size:%s landscape;margin:0}html,body{margin:0;background:#fff}", tn_paper);
        printf(".pg{position:relative;width:%smm;height:%smm;overflow:hidden;font:8.5pt Arial,sans-serif;color:#000}", f3(tn_pw), f3(tn_ph));
        printf(".hd{position:absolute;left:10mm;top:6mm;right:10mm}.hd b{font-size:11pt}.hd span{color:#444}");
        printf(".bd{position:absolute;left:%smm;top:%smm;width:%smm;height:%smm}", f3(x), f3(y), f3(vb_w), f3(vb_h));
        printf(".sc{position:absolute;left:10mm;bottom:7mm;width:50mm;height:2.5mm;box-sizing:border-box;border:.3mm solid #000;border-top:none}");
        printf(".sc i{position:absolute;left:52mm;top:-1mm;font-style:normal;white-space:nowrap}");
        printf("</style></head><body><div class=\"pg\">");
        printf("<div class=\"hd\"><b>%s</b> &middot; %s &middot; %s<br><span>%s</span></div>",
               h(title), h(mir), h(fn_disp), h("1:1 · " + board_size_txt() + " mm · " + tn_paper + " · " + fk_title()));
        string tr = "";
        if (mirror) tr = " style=\"transform:scaleX(-1)\"";
        printf("<svg class=\"bd\"%s xmlns=\"http://www.w3.org/2000/svg\" viewBox=\"%s %s %s %s\">", tr, f4(vb_x), f4(vb_y), f4(vb_w), f4(vb_h));
        // без масок: тёмная полярность — чёрная, светлая (вырезы) — белая, фон листа белый
        printf("<g transform=\"%s\">", vb_flip);
        if (kind != 3) gerber_body(gf_src[gi], "#000", "#fff");
        if (ko >= 0) gerber_body(gf_src[ko], "#000", "#fff");
        printf("</g>");
        printf("<g transform=\"%s\">", vb_flip);
        for (int i = 0; i < n_hole; i++) {
            if (kind == 0) {
                // метка для сверла: белая точка в центре площадки
                real r = hl_d[i] * 0.3;
                if (r < 0.15) r = 0.15;
                if (r > 0.4) r = 0.4;
                printf("<circle cx=\"%s\" cy=\"%s\" r=\"%s\" fill=\"#fff\"/>", f4(hl_x[i]), f4(hl_y[i]), f4(r));
            } else if (kind == 3) {
                printf("<circle cx=\"%s\" cy=\"%s\" r=\"%s\" fill=\"none\" stroke=\"#000\" stroke-width=\"0.08\"/><circle cx=\"%s\" cy=\"%s\" r=\"0.12\" fill=\"#000\"/>",
                       f4(hl_x[i]), f4(hl_y[i]), f4(hl_d[i] / 2), f4(hl_x[i]), f4(hl_y[i]));
            }
        }
        printf("</g></svg>");
        printf("<div class=\"sc\"><i>50 mm &mdash; %s</i></div>", h(L("проверить масштаб", "check the scale")));
        printf("</div></body></html>\n");
    }
    html_to_pdf(html, pdf);
}

// все листы: медь, шелкография, маска (плёночная УФ-маска), карта сверловки
int n_toner = 0;

void toner_all()
{
    if (n_gf == 0) { fn_err += "Toner: no Gerber. "; return; }
    shell("mkdir " + qp(fn_d4) + " 2>nul");
    toner_paper();
    int dx = gf_find("XLN");
    if (dx >= 0) excellon_parse(gf_src[dx]);
    else n_hole = 0;
    string pre = fn_d4 + "/" + fn_fbase + "_";
    string th = fn_tmp + "/toner_";
    n_toner = 0;
    int i;
    i = gf_find("GTL"); if (i >= 0) { toner_sheet(th + "1.html", pre + "01_TOP_COPPER_mirrored.pdf", i, L("Медь, верх", "Top copper"), 1, 0); n_toner++; }
    i = gf_find("GBL"); if (i >= 0) { toner_sheet(th + "2.html", pre + "02_BOTTOM_COPPER.pdf", i, L("Медь, низ", "Bottom copper"), 0, 0); n_toner++; }
    i = gf_find("GTO"); if (i >= 0 && gf_size[i] > 400) { toner_sheet(th + "3.html", pre + "03_TOP_SILK_mirrored.pdf", i, L("Шелкография, верх", "Top silkscreen"), 1, 1); n_toner++; }
    i = gf_find("GBO"); if (i >= 0 && gf_size[i] > 400) { toner_sheet(th + "4.html", pre + "04_BOTTOM_SILK.pdf", i, L("Шелкография, низ", "Bottom silkscreen"), 0, 1); n_toner++; }
    i = gf_find("GTS"); if (i >= 0 && gf_size[i] > 400) { toner_sheet(th + "5.html", pre + "05_TOP_SOLDERMASK_UV_mirrored.pdf", i, L("Маска (УФ), верх: вскрытия чёрные", "Top solder mask (UV): openings black"), 1, 2); n_toner++; }
    i = gf_find("GBS"); if (i >= 0 && gf_size[i] > 400) { toner_sheet(th + "6.html", pre + "06_BOTTOM_SOLDERMASK_UV.pdf", i, L("Маска (УФ), низ: вскрытия чёрные", "Bottom solder mask (UV): openings black"), 0, 2); n_toner++; }
    if (dx >= 0) { toner_sheet(th + "7.html", pre + "07_DRILL_GUIDE.pdf", dx, L("Карта сверловки (вид сверху)", "Drill guide (top view)"), 0, 3); n_toner++; }
}

// ---------------------------------------------------------------- ЛУТ: инструкция

string TONER_CSS =
    "body{font:15px/1.55 'Segoe UI',Arial,sans-serif;color:#1c2127;background:#f6f4ef;margin:0}" +
    ".w{max-width:860px;margin:0 auto;padding:30px 24px}h1{font-size:26px;margin:0 0 4px}.en{display:block;color:#7d8792;font-size:.85em}" +
    ".box{background:#fff;border:1px solid #e4e2dd;border-radius:14px;padding:16px 20px;margin:16px 0}" +
    "li{margin:6px 0}code{background:#efede7;padding:1px 6px;border-radius:5px}b.m{color:#b04a3e}";

void toner_page(string dst)
{
    string files[];
    int n = fileglob(files, fn_d4 + "/*.pdf");
    output(dst, "wt") {
        printf("<!DOCTYPE html><html lang=\"%s\"><head><meta charset=\"utf-8\"><title>%s</title><style>%s</style></head><body><div class=\"w\">",
               LANG_CODE[ui_lang], h(fn_disp + " · " + L("ЛУТ 1:1", "Toner transfer 1:1")), TONER_CSS);
        printf("<h1>%s</h1>", h(L("Листы для ЛУТ, масштаб 1:1", "Toner transfer prints, scale 1:1")));
        printf("<div class=\"box\"><ol>");
        printf("<li>%s</li>", h(L("Печатать на лазерном принтере в масштабе 100% («Фактический размер»). «Вписать в страницу» не включать.",
                                  "Print on a laser printer at 100% / Actual size. Never use Fit to page.")));
        printf("<li>%s</li>", h(Lf("Проверить масштаб линейкой: шкала внизу листа — 50 мм, контур платы {0} мм.",
                                   "Check the scale with a ruler: the bar at the bottom of each sheet is 50 mm, the board outline is {0} mm.", board_size_txt(), "", "")));
        printf("<li>%s</li>", h(L("Листы построены из тех же Gerber, что уходят на завод: заливки, зазоры и вырезы — точные. Белые точки — центры отверстий для сверла.",
                                  "Sheets are built from the same Gerber files the factory gets: copper pours, clearances and cut-outs are exact. White dots mark drill centres.")));
        printf("<li>%s</li>", h(L("Листы TOP уже зеркальные: после переноса утюгом изображение на плате читается правильно.",
                                  "TOP sheets are already mirrored: after ironing the image reads correctly on the board.")));
        printf("<li>%s</li>", h(L("Листы BOTTOM напечатаны как вид сверху — для нижней стороны это и есть нужное зеркало.",
                                  "BOTTOM sheets are printed as seen from the top — this is already the correct mirror for the bottom side.")));
        printf("<li>%s</li>", h(L("Стороны совмещать по отверстиям (лист DRILL); при необходимости сначала просверлить.",
                                  "Align the two sides through the drill holes (DRILL sheet), drill first if needed.")));
        printf("<li>%s</li>", h(L("Бумага: глянцевая/фото или термотрансферная плёнка; утюг 160–180 °C.",
                                  "Paper: glossy/photo or transfer film; iron 160–180 °C.")));
        if (fn_layers > 2) printf("<li><b class=\"m\">%s</b></li>",
               h(Lf("Слоёв меди у платы: {0}. Дома делаются только двусторонние платы — листы только для внешних слоёв (для справки или упрощённого макета).",
                    "The board has {0} copper layers: at home only double-sided boards can be made — these sheets cover the outer layers only (for reference or a simplified prototype).",
                    istr(fn_layers), "", "")));
        printf("</ol></div><div class=\"box\"><b>%s</b><ul>", h(L("Файлы", "Files")));
        for (int i = 0; i < n; i++) printf("<li><a href=\"%s\">%s</a></li>", replace_all(filename(files[i]), " ", "%20"), h(filename(files[i])));
        printf("</ul></div><p class=\"en\">%s</p></div></body></html>\n", h(fk_sign()));
    }
}

// ---------------------------------------------------------------- стартовая страница

string IDX_CSS =
    "body{margin:0;font:15px/1.5 'Segoe UI',Arial,sans-serif;background:#14181d;color:#e9edf0}" +
    ".w{max-width:980px;margin:0 auto;padding:38px 24px}.brand{font-size:12.5px;letter-spacing:.1em;text-transform:uppercase;color:#9aa6b1;display:flex;gap:9px;align-items:center}" +
    ".brand i{width:9px;height:9px;border-radius:50%;background:#88ed77;box-shadow:0 0 10px #88ed77}" +
    "h1{font-size:32px;margin:10px 0 2px}.en{display:block;color:#8d98a3;font-size:.85em}" +
    ".g{display:grid;grid-template-columns:repeat(auto-fit,minmax(280px,1fr));gap:14px;margin-top:26px}" +
    "a.c{display:block;background:#1d232b;border:1px solid #2b333c;border-radius:16px;padding:18px 20px;color:#e9edf0;text-decoration:none;transition:transform .25s,border-color .25s;animation:r .6s both}" +
    "a.c:hover{transform:translateY(-3px);border-color:#88ed77}a.c b{display:block;font-size:17px;margin-bottom:4px}" +
    "a.c small{color:#8d98a3}.n{font:700 12px Consolas,monospace;color:#88ed77}" +
    ".rnd{position:relative;margin:26px 0 0;max-width:720px}.rnd img{position:absolute;inset:0;width:100%;height:100%}.rnd img:first-child{position:relative;display:block}" +
    "@keyframes r{from{opacity:0;transform:translateY(8px)}}footer{color:#6f7a85;font-size:12px;margin-top:34px}";

string idx_card(string href, string no, string title, string sub)
{
    return "<a class=\"c\" href=\"" + replace_all(href, " ", "%20") + "\"><span class=\"n\">" + no + "</span><b>" + h(title) +
           "</b><small>" + h(sub) + "</small></a>";
}

void index_page(string dst)
{
    output(dst, "wt") {
        printf("<!DOCTYPE html><html lang=\"%s\"><head><meta charset=\"utf-8\"><meta name=\"viewport\" content=\"width=device-width,initial-scale=1\">", LANG_CODE[ui_lang]);
        printf("<title>%s</title><style>%s</style></head><body><div class=\"w\">", h(fn_disp + " · FabKit"), IDX_CSS);
        printf("<div class=\"brand\"><i></i>%s</div>", h(fk_sign()));
        printf("<h1>%s<span class=\"en\">%s</span></h1>", h(fn_disp), h(L("Производственный пакет", "Production package") + " · " + st_get("date")));
        if (n_gf > 0) printf("<div class=\"rnd\"><img src=\"02_REPORT/img/top_flat.svg\" alt=\"\"></div>");
        printf("<div class=\"g\">");
        if (n_gf > 0) printf("%s", idx_card("01_JLCPCB_ORDER/JLCPCB_GERBER/" + fn_fbase + "_Gerber_JLCPCB.zip", "01", L("Gerber для JLCPCB", "Gerber for JLCPCB"),
                                            fn_fbase + "_Gerber_JLCPCB.zip"));
        printf("%s", idx_card("01_JLCPCB_ORDER/" + fn_fbase + "_JLCPCB_BOM.csv", "01", L("BOM для сборки", "Assembly BOM"), fn_fbase + "_JLCPCB_BOM.csv"));
        printf("%s", idx_card("01_JLCPCB_ORDER/" + fn_fbase + "_JLCPCB_CPL.csv", "01", L("CPL (координаты)", "CPL (pick & place)"), fn_fbase + "_JLCPCB_CPL.csv"));
        printf("%s", idx_card("02_REPORT/" + fn_fbase + "_Report.html", "02", L("Отчёт", "Report"), L("BOM, цены, замены, слои", "BOM, prices, substitutes, layers")));
        if (opt_docs) {
            string d = "03_ASSEMBLY_DOCS/" + fn_fbase + "_Assembly_A4.pdf";
            if (!file_exists(fn_out + "/" + d)) d = "03_ASSEMBLY_DOCS/" + fn_fbase + "_Assembly_A4.html";
            printf("%s", idx_card(d, "03", L("Документация A4", "A4 documentation"), L("чертежи, порядок пайки, ключи", "drawings, soldering order, keys")));
        }
        if (opt_toner) printf("%s", idx_card("04_TONER_TRANSFER_1to1/HOW_TO_PRINT.html", "04", L("ЛУТ 1:1", "Toner transfer 1:1"), L("PDF слоёв", "layer PDFs")));
        if (fn_bk_zip != "")
            printf("%s", idx_card("05_BACKUP/", "05", L("Бэкап проекта", "Design backup"),
                                  addin_alive() ? L("схема и плата EAGLE, STEP платы, вся облачная папка", "EAGLE schematic and board, board STEP, the whole cloud folder")
                                                : L("схема и плата EAGLE, zip", "EAGLE schematic and board, zip")));
        printf("</div><footer>%s</footer></div></body></html>\n", h(fk_sign()));
    }
}

// ---------------------------------------------------------------- вход третьей фазы

void finish_main(string stfile)
{
    st_load(stfile);
    ui_lang = st_geti("lang");                 // язык первой фазы (в т. ч. из -lang)
    if (ui_lang < 0 || ui_lang >= N_LANG) ui_lang = 0;
    fn_out = st_get("outdir"); fn_tmp = st_get("tmp"); fn_base = st_get("base");
    fn_fbase = st_get("fbase");
    if (fn_fbase == "") fn_fbase = fn_base;
    fn_d1 = fn_out + "/01_JLCPCB_ORDER"; fn_d2 = fn_out + "/02_REPORT"; fn_d3 = fn_out + "/03_ASSEMBLY_DOCS"; fn_d4 = fn_out + "/04_TONER_TRANSFER_1to1";
    fn_outline = fn_tmp + "/outline.txt";
    if (file_exists(st_get("runner"))) fk_runner = st_get("runner");
    if (!file_exists(fn_out)) {
        if (!st_geti("batch")) dlgMessageBox("dmxON FabKit: " + L("нет папки пакета", "package folder not found") + "\n" + fn_out, "OK");
        return;
    }
    opt_gerber = st_geti("gerber"); opt_docs = st_geti("docs"); opt_toner = st_geti("toner"); opt_pdf = st_geti("pdf");
    opt_open = st_geti("open"); batch_mode = st_geti("batch"); opt_boards = st_geti("boards");
    opt_mask = st_get("mask"); opt_silk = st_get("silk"); opt_finish = st_get("finish"); opt_thick = st_get("thick");
    tb_product = st_get("tb_product"); tb_docno = st_get("tb_docno"); tb_company = st_get("tb_company"); tb_designer = st_get("tb_designer");
    tb_checker = st_get("tb_checker"); tb_approver = st_get("tb_approver"); tb_customer = st_get("tb_customer"); tb_rev = st_get("tb_rev"); tb_note = st_get("tb_note");
    fn_disp = ver_disp(fn_base, tb_rev);
    tb_pcbno = st_get("tb_pcbno");
    doc_std = st_geti("std");
    if (doc_std < 0 || doc_std >= N_STD) doc_std = 0;
    dc_a3 = st_geti("a3");
    dc_class = st_geti("class");
    if (dc_class < 1) dc_class = 2;
    log_txt = "";
    n_gf = 0;

    // листам ЛУТ тоже нужны Gerber
    if (opt_gerber || opt_toner) finish_gerber();
    if (fn_layers == 0) fn_layers = st_geti("layers");      // без Gerber — по слоям платы
    dfm_check();

    if (opt_toner) {
        fk_log("toner 1:1");
        toner_all();
        toner_page(fn_d4 + "/HOW_TO_PRINT.html");
    }

    fk_log("report");
    shell("mkdir " + qp(fn_d2) + " 2>nul");
    assemble_report(fn_tmp + "/report_p1.html", fn_d2 + "/" + fn_fbase + "_Report.html");

    if (opt_docs) {
        fk_log("A4 docs");
        shell("mkdir " + qp(fn_d3) + " 2>nul");
        string dh = fn_d3 + "/" + fn_fbase + "_Assembly_A4.html";
        assemble_docs(fn_tmp + "/docs_p1.html", dh);
        if (opt_pdf) {
            fk_log("PDF");
            html_to_pdf(dh, fn_d3 + "/" + fn_fbase + "_Assembly_A4.pdf");
        }
    }

    // бэкап проекта — сам FabKit, в 05_BACKUP; надстройка dmxON добавит туда же всю облачную папку
    string bk = "";
    if (st_geti("backup")) {
        fk_log("backup");
        backup_design();
        if (fn_bk_zip != "") bk = L("Бэкап проекта (схема и плата):", "Design backup (schematic and board):") + " " + fn_bk_zip;
        else bk = L("Бэкап проекта не записан — нет файла платы.", "Design backup not written — no board file.");
        if (addin_alive()) {
            addin_request("backup", ",\"tool\":\"fabkit\",\"out\":" + json_s(fn_out) + ",\"name\":" + json_s(zip_base(fn_fbase) + "_cloud") +
                                    ",\"step\":" + json_s(zip_base(fn_fbase) + ".step"));
            bk += "\n" + L("Надстройка dmxON добавит туда же STEP платы с деталями и всю облачную папку проекта (3D, чертежи, файлы).",
                           "The dmxON add-in adds the board STEP with its parts and the whole cloud design folder there too (3D, drawings, files).");
        }
        fk_log(bk);
    }

    index_page(fn_out + "/index.html");
    output(fn_out + "/" + FK_MARKER, "wt") printf("%s\n%s\n", fk_title(), st_get("date"));
    if (!st_geti("keep_tmp")) shell("rmdir /s /q " + qp(fn_tmp));

    if (opt_open && !batch_mode) system("explorer.exe \"" + to_win(fn_out) + "\"");
    if (batch_mode) return;
    string msg = st_get("summary");
    if (bk != "") msg += "\n\n" + bk;
    if (n_gf > 0) msg += "\n\nGerber: " + Lf("файлов: {0}, слоёв меди: {1}", "{0} files, {1} copper layers", istr(n_gf), istr(fn_layers), "");
    if (fn_err != "") msg += "\n\n" + fn_err;
    msg += "\n\n" + replace_all(fn_out, "\\", "/");
    dlgMessageBox(msg, "OK");
}

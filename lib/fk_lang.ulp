// fk_lang.ulp — переводы интерфейса: испанский, немецкий, польский (русский и английский — в коде)
// dmxON FabKit · dmxON by AlexSmith 2026 · см. LICENSE.md
// Создаётся из lang/strings.tsv (ключ — английский текст); правьте TSV, не этот файл.

string TR_EN[] = {
    " and on the board",
    "100 % electrical test of all nets per IPC-9252B.",
    "1:1 toner-transfer sheets (PDF)",
    "A4 documentation",
    "A4 documentation for manual assembly",
    "About",
    "Align the two sides through the drill holes (DRILL sheet), drill first if needed.",
    "Already installed — «Install» updates the files.",
    "Alternatives are searched for parts that are missing, out of stock or have a non-fitting package. An alternative is accepted only if its JLC library footprint matches the board pads. The cheapest one for the whole batch wins.",
    "and CPL (pick & place)",
    "anode and cathode",
    "applied",
    "Apply cheaper compatible substitutes for missing parts",
    "Approved by",
    "Assemble and solder per IPC J-STD-001J, Class {0}; acceptance per IPC-A-610J, Class {0}.",
    "Assembly BOM",
    "Assembly drawing",
    "Assembly instruction",
    "Assembly side",
    "assembly variant: do not place",
    "Assembly: BOM",
    "Attention",
    "attribute",
    "Attribute part number contradicts the value — reselect",
    "attribute {0} — replaced with {1} by value",
    "Back up the design into the package (05_BACKUP): schematic and board; with the dmxON add-in, the board STEP and the whole cloud folder",
    "Base material",
    "Base material: FR-4 per IPC-4101F/21; board thickness {0} mm ±10 %.",
    "Batch",
    "Batteries",
    "Bill of materials",
    "black",
    "blue",
    "Blue — board pads, orange outline — the JLC (EasyEDA) library footprint after alignment. Cross — footprint origin on the board, orange circle — JLC part centre written to the CPL. Dots mark pin 1. Rotation fixed for {0}, centre for {1} parts.",
    "Blue — board pads, orange — the substitute footprint.",
    "Board",
    "Board outline",
    "Board outline, pads, bodies and designators. Red dot marks pin 1 or the cathode. The bottom side is shown as seen from the solder side (mirrored).",
    "board package {0} but the part is {1}",
    "Board → JLC",
    "Boards in the order",
    "BOM import: {0} designators.",
    "BOM lines",
    "BOM, prices, substitutes, layers",
    "bottom",
    "Bottom (as seen from below)",
    "Bottom copper",
    "Bottom paste (stencil)",
    "BOTTOM sheets are printed as seen from the top — this is already the correct mirror for the bottom side.",
    "Bottom side",
    "Bottom side: SMD parts",
    "Bottom silkscreen",
    "Bottom solder mask",
    "Bottom solder mask (UV): openings black",
    "Bottom view (solder side)",
    "bottom-left",
    "bottom-right",
    "bottom-side part: check rotation in the JLCPCB preview",
    "Bow and twist max {0} % (board with surface-mount parts).",
    "Browse…",
    "Build package",
    "Bulky SMD: electrolytics, power inductors, SMD connectors",
    "by number prefix",
    "by part number",
    "by shape",
    "by value",
    "Cancel",
    "Cannot copy the files to:",
    "Cannot create the folder:",
    "Cannot find the user folder.",
    "Cannot install the dmxON add-in to:",
    "Capacitors",
    "Catalogue",
    "catalogue has {0} (check the suffix)",
    "Catalogue requests: {0}, method: {1}, unanswered: {2}.",
    "cathode",
    "center",
    "check the pinout",
    "check the scale",
    "Check the scale with a ruler: the bar at the bottom of each sheet is 50 mm, the board outline is {0} mm.",
    "check: {0}, but the value is {1}",
    "Checked by",
    "checking",
    "Circuit diagram",
    "Circuit diagram in the documentation",
    "Clear it? «No» — create a new dated folder.",
    "Company",
    "Compatibility",
    "compatible substitute {0} available (not applied, enable substitutes in the settings)",
    "Component placement",
    "Components",
    "components",
    "Conductive pattern per Gerber data {0} (RS-274X); hole positions per the Excellon file.",
    "Connectors",
    "Copied",
    "copper extends {0} mm beyond the board outline",
    "Copper layers",
    "Copper layers: {0}; outer copper 35 µm (1 oz) finished; layer structure per table.",
    "Copying the code, modification and commercial use are not permitted.",
    "Cost",
    "CPL (pick & place)",
    "CPL at pad centre when the footprint is not verified",
    "Created by",
    "Crystals and resonators",
    "Customer",
    "Date of issue",
    "Design backup",
    "Design backup (schematic and board):",
    "Design backup not written — no board file.",
    "Designation",
    "Designator",
    "designator in the skip list",
    "Designators",
    "Designators & notes",
    "designators on details {0}…{1}",
    "Designed by",
    "detail",
    "Diagnostics",
    "Diameter, mm",
    "differs",
    "Dimensions, mm",
    "Diodes",
    "dmxON FabKit removed.",
    "DNP / JLC_EXCLUDE attribute",
    "Do not fit parts not listed in parts list {0}.",
    "Do not fit parts not listed in {0}.",
    "Document list",
    "Document No.",
    "Document status",
    "Document type",
    "Documentation",
    "does not fit",
    "Done.",
    "Drawing title block (this board)",
    "drawings, soldering order, keys",
    "Drill (plated + non-plated)",
    "Drill guide (top view)",
    "Drill map",
    "Drilling",
    "EAGLE schematic and board, board STEP, the whole cloud folder",
    "EAGLE schematic and board, zip",
    "EasyEDA model could not be parsed",
    "ENIG per IPC-4552B",
    "Every layer on its own",
    "Excluded",
    "Extended feeder fee, $",
    "Extended loading ({0})",
    "extends {0} mm beyond the outline — the fab will clip it",
    "FabKit is free. If it saved you time or money, please support new versions.",
    "Fabricate per GOST R 53429-2009, accuracy class {0}; quality per IPC-6012F, Class {1}; acceptance per IPC-A-600M.",
    "Fabricate per IPC-6012F, Class {0}; acceptability per IPC-A-600M, Class {0}.",
    "Fabrication drawing",
    "Fields can also be edited later right in the documentation HTML.",
    "File",
    "File numbers override attributes. Reads «Download Selected Parts List» and any CSV/XLSX with Designator and LCSC.",
    "Files",
    "Files are named the way JLCPCB expects (Protel: GTL, GBL, G1…, GTS, GTP, GTO, GKO, XLN). Toggle layers on the left.",
    "Files for JLCPCB",
    "File…",
    "Fine-pitch ICs (QFN, QFP, pitch ≤ 0.65 mm)",
    "First used",
    "Flux and paste or drag-solder; inspect for bridges. Exposed pad — hot air.",
    "Folder",
    "folder",
    "footprint differs from JLC: some leads partly outside pads (up to {0} mm)",
    "footprint does not fit",
    "footprint is a mirror image of the part package ({0})",
    "footprint match",
    "footprint matches by pin numbers",
    "footprint matches by shape — check the pinout and the mating part",
    "footprint not verified",
    "footprint notes",
    "footprint {0} does not fit package {1}, deviation up to {2} mm",
    "footprint {0} has no paste (tCream) — the stencil will not apply paste, check the library",
    "footprints",
    "Footprints",
    "Footprints and orientation",
    "Format",
    "found",
    "Free to use with attribution.",
    "from attributes",
    "from attributes / import",
    "Fuses",
    "Fusion source",
    "Gerber",
    "Gerber and drill for JLCPCB (zip + layer previews)",
    "Gerber for JLCPCB",
    "Gerber layers and drilling",
    "Gerber was not exported",
    "green",
    "Handle electrostatic-sensitive devices per IEC 61340-5-1:2024.",
    "HASL (tin-lead)",
    "Holes",
    "Hover to explode the layer stack",
    "Identification number",
    "Import a finished JLCPCB BOM (optional)",
    "imported BOM",
    "In the JLCPCB preview check rotation of parts listed under Attention.",
    "Inductors and ferrite beads",
    "Inner copper {0}",
    "Install",
    "Installation",
    "Installation into Autodesk Fusion:",
    "Integrated circuits",
    "Issue",
    "Item",
    "JLC has no footprint model",
    "JLC model has no pads",
    "JLCPCB BOM",
    "JLCPCB catalogue",
    "JLCPCB catalogue did not answer",
    "JLCPCB catalogue prices at export time, for {0} boards, without attrition, PCB and assembly cost. Each unique Extended part adds a feeder loading fee ({1}).",
    "JLCPCB catalogue: off",
    "JLCPCB catalogue: online",
    "Key",
    "Key: 1 — pin 1, K — cathode, the arrow shows where it is from the body centre.",
    "Lang.",
    "Language",
    "Large thermal mass: more heat; electrolytic polarity.",
    "Layer",
    "layer PDFs",
    "Layers",
    "LCSC part selection",
    "LCSC_PART attributes written",
    "LCSC_PART attributes written: {0}.",
    "lead-free HASL",
    "Lead-free, RoHS compliant (Directive 2011/65/EU).",
    "LEDs",
    "left",
    "Legal owner",
    "library",
    "Lines without a catalogue price: {0}.",
    "List of elements",
    "Lot",
    "Manufacturability check",
    "Manufacturer",
    "Manufacturing and assembly documentation package",
    "Mass",
    "match",
    "Matched by",
    "Min capacitor voltage, V",
    "Min hole size, mm",
    "min hole {0} mm is below the standard 0.3 mm for 1–2 layers",
    "min hole {0} mm — standard",
    "min hole {0} mm: fine for multilayer, holes below 0.3 mm may raise the price",
    "Min track width, mm",
    "Mind diode and LED polarity (cathode mark).",
    "Minimum conductor width {0} mm; minimum finished hole {1} mm.",
    "MIRRORED",
    "mirrored",
    "mm",
    "Most expensive lines",
    "mounting hole / fiducial",
    "Name",
    "Need",
    "need attention",
    "Need attention",
    "No",
    "no answer from EasyEDA",
    "no answer from JLCPCB, part number not verified",
    "No issues.",
    "No output folder.",
    "no pads (logo, artwork)",
    "no part number",
    "no substitute: no in-stock alternative has a compatible footprint",
    "No substitutes needed.",
    "not applied",
    "Not exported to BOM/CPL",
    "not found",
    "not found by value; MPN attribute {0} not used: the value points to a different part",
    "not in the JLCPCB catalogue",
    "not mirrored",
    "Note",
    "Notes",
    "Nothing.",
    "Offset, mm",
    "Open the folder when done",
    "Order",
    "Order code",
    "Ordering at JLCPCB",
    "Original",
    "OSP (organic solderability preservative)",
    "Other ICs and transistors (SOIC, SOT, TSSOP)",
    "Other items",
    "Other parts",
    "Other SMD: 1206+, diodes, LEDs, crystals",
    "Outer copper weight",
    "Outline tolerance ±{0} mm; dimensions in millimetres.",
    "Output",
    "Output folder",
    "Overlay",
    "Package",
    "package folder not found",
    "pads without paste (fiducial, jumper, contact pad)",
    "Paper size",
    "Paper: glossy/photo or transfer film; iron 160–180 °C.",
    "part",
    "Part",
    "Part #",
    "part leads without board pads: {0}",
    "Part number",
    "part number taken from MPN attribute {0}",
    "Parts",
    "Parts cost (estimate)",
    "Parts list",
    "parts, estimate",
    "PCB",
    "PCB layers",
    "PCB order options",
    "PCB parameters for the order form",
    "PCB part number",
    "PCB qty",
    "PCB thickness, mm",
    "PCB: archive",
    "PDF of the documentation (via Microsoft Edge)",
    "per board",
    "Per board",
    "phase 2: Fusion export",
    "phase 2: the dmxON add-in exports Gerber",
    "pin 1",
    "Pin 1 and polarity keys",
    "pin numbers",
    "pin numbers differ",
    "Placement",
    "polar part rotated by {0}° from pad numbers 1/2 — two-pin libraries number pads differently, check the polarity mark in the preview",
    "polarity cannot be derived from the shape — check in the JLCPCB preview",
    "Prefer Basic/Preferred (no feeder fee)",
    "Prepared with: {0}",
    "Print on a laser printer at 100% / Actual size. Never use Fit to page.",
    "Printed circuit board",
    "Product",
    "Production package",
    "Production report",
    "purple",
    "Purpose",
    "Qty",
    "Reason",
    "red",
    "Ref. designation",
    "Ref. No.",
    "Reference designation",
    "Reference designations as in the circuit diagram (GOST 2.710-81); a dot marks pin 1 or the cathode.",
    "Reference designations as in the circuit diagram (letter codes per IEC 81346-2:2019); a dot marks pin 1 or the cathode.",
    "Relays",
    "Remove",
    "Remove flux residues after soldering unless a no-clean flux is used.",
    "report",
    "Report",
    "request {0} of {1}",
    "Resistors",
    "Restart Fusion once after installing.",
    "Restart Fusion to remove the dmxON tab.",
    "Restart Fusion — the dmxON tab appears in the PCB and schematic editors, and {0} in Automation → Run ULP.",
    "Result",
    "Rev.",
    "right",
    "Rotation",
    "rotation offset {0} from attribute/map replaced by computed {1}",
    "Run dmxON FabKit from the board editor.",
    "Scale",
    "schematic",
    "Search the JLCPCB catalogue (online)",
    "searching substitutes",
    "see drawing",
    "shape",
    "shape matches but pin numbers do not — check the pinout",
    "Share",
    "Shared by all boards",
    "sheet",
    "Sheet",
    "Sheets",
    "Sheets are built from the same Gerber files the factory gets: copper pours, clearances and cut-outs are exact. White dots mark drill centres.",
    "Silkscreen",
    "Size",
    "Skip designators",
    "Small passives (0201–0805)",
    "solder jumper / test point",
    "Solder mask",
    "Solder mask colour",
    "Solder mask: LPI per IPC-SM-840E, Class T, {0}, both sides; legend in non-conductive ink, {1}.",
    "Solder the side with fewer and lighter parts first.",
    "Soldering order — step {0} of {1}",
    "Soldering sequence and pin 1 keys per {0}.",
    "Source",
    "Specification",
    "Stage",
    "Standard",
    "Stock",
    "stock {0} < needed {1}",
    "stock {0} of {1}",
    "Store and bake moisture-sensitive devices per IPC/JEDEC J-STD-033D (MSL per J-STD-020F).",
    "substitute",
    "Substitute",
    "SUBSTITUTE",
    "substitutes",
    "Substitutes",
    "Substitutes (JLCPCB catalogue alternatives)",
    "Support the project",
    "Surface finish",
    "Surface finish: {0}; solderability per J-STD-003D.",
    "Switches",
    "Tack one pin, align to the pin-1 key, then solder the rest.",
    "The board has {0} copper layers: at home only double-sided boards can be made — these sheets cover the outer layers only (for reference or a simplified prototype).",
    "the board text says version {0}, the package is version {1}",
    "the board text says version {0}, the package is version {1}: fix the text or the version on the title block tab.",
    "the design attribute REV is {0}, the package is version {1}: run FabKit from its dialog to save the version in the design",
    "The dmxON add-in adds the board STEP with its parts and the whole cloud design folder there too (3D, drawings, files).",
    "the dmxON add-in is installed: the <b>dmxON</b> tab appears in the PCB and schematic editors — FabKit, JLC Rules, backup of the design folder, updates from GitHub",
    "The dmxON add-in is updated — restart Fusion to run the new version.",
    "the dmxON folders are added to Fusion's ULP, design rules and CAM lists — <b>{0}</b> is also in Automation → Run ULP; the built-in ULPs stay",
    "The dmxON tab is already running and {0} is updated — it is also in Automation → Run ULP.",
    "The folder exists and was not created by FabKit:",
    "The package goes to «{0}»: the version is set on the title block tab and appears in every file name and title block; a previous package of this version is replaced completely.",
    "the project is copied to <tt>{0}</tt>",
    "Thickness, mm",
    "Through-hole (THT) parts",
    "through-hole part (THT disabled)",
    "Through-hole parts (THT) — last",
    "THT parts last, after cleaning SMD; low parts before tall ones.",
    "Title",
    "Title block fields are editable here, then Ctrl+P → Save as PDF (margins: none).",
    "Title, supplementary title",
    "Toner transfer 1:1",
    "Toner transfer prints, scale 1:1",
    "Tool",
    "top",
    "Top",
    "top / bottom",
    "Top copper",
    "Top paste (stencil)",
    "TOP sheets are already mirrored: after ironing the image reads correctly on the board.",
    "Top side",
    "Top silkscreen",
    "Top solder mask",
    "Top solder mask (UV): openings black",
    "Top view",
    "top-left",
    "top-right",
    "Total",
    "track width from {0} mm — at the capability limit",
    "track width from {0} mm — standard",
    "track width {0} mm is below the {1} mm minimum",
    "Transformers",
    "Transistors",
    "Tweezers and a fine tip; tack one side, then the other.",
    "Type",
    "Unit",
    "Used in the report, the order parameters and the board render.",
    "value",
    "Value",
    "Verify footprints against JLC; CPL rotation and centre from them",
    "Version",
    "Version (Rev.)",
    "Version {0} saved in the design (attribute REV).",
    "version {0} — in file names and title blocks{1}",
    "View",
    "WARNING",
    "What goes into BOM/CPL",
    "What to build",
    "What to upload",
    "Where",
    "white",
    "Write part numbers to LCSC_PART attributes",
    "yellow",
    "Yes",
    "Zone",
    "{0} apertures · {1} lines · {2} flashes",
    "{0} copper strokes thinner than 0.05 mm (artwork, logo) will not be reproduced",
    "{0} files, {1} copper layers",
    "{0} is not in the JLCPCB catalogue",
    "{0} is outside the board outline",
    "{0} is rated {1} V, {2} V required",
    "{0} regions",
    "{0} requests via curl...",
    "{0} tools · {1} holes",
    "{0}, but the value is {1}",
    "{0}; no replacement by value, kept {1}"
};

string TR_ES[] = {
    " y en la placa",
    "Prueba eléctrica del 100 % de las redes según IPC-9252B.",
    "Hojas 1:1 para transferencia de tóner (PDF)",
    "Documentación A4",
    "Documentación A4 para montaje manual",
    "Acerca de",
    "Alinee las dos caras mediante los taladros (hoja DRILL); si hace falta, taladre primero.",
    "Ya instalado — «Instalar» actualiza los archivos.",
    "Se buscan alternativas para las piezas que faltan, sin stock o con un encapsulado que no encaja. Una alternativa solo se acepta si su huella de la biblioteca JLC coincide con los pads de la placa. Gana la más barata para todo el lote.",
    "y CPL (pick & place)",
    "ánodo y cátodo",
    "aplicado",
    "Aplicar sustitutos compatibles más baratos para piezas faltantes",
    "Aprobado por",
    "Montar y soldar según IPC J-STD-001J, clase {0}; aceptación según IPC-A-610J, clase {0}.",
    "BOM de montaje",
    "Plano de montaje",
    "Instrucción de montaje",
    "Cara de montaje",
    "variante de montaje: no montar",
    "Montaje (PCB Assembly): BOM",
    "Atención",
    "atributo",
    "El número del atributo contradice el valor — volver a seleccionar",
    "atributo {0} — sustituido por {1} según el valor",
    "Copia del diseño en el paquete (05_BACKUP): esquema y placa; con el complemento dmxON, el STEP de la placa y toda la carpeta en la nube",
    "Material base",
    "Material base: FR-4 según IPC-4101F/21; espesor de la placa {0} mm ±10 %.",
    "Lote",
    "Baterías",
    "Lista de materiales (BOM)",
    "negro",
    "azul",
    "Azul — pads de la placa; contorno naranja — huella de la biblioteca JLC (EasyEDA) tras la alineación. Cruz — origen de la huella en la placa; círculo naranja — centro de la pieza JLC, que se escribe en el CPL. Los puntos marcan el pin 1. Rotación corregida en {0} piezas, centro en {1}.",
    "Azul — pads de la placa, naranja — huella del sustituto.",
    "Placa",
    "Contorno de la placa",
    "Contorno de la placa, pads, cuerpos y designadores. El punto rojo marca el pin 1 o el cátodo. La cara inferior se muestra vista desde el lado de soldadura (espejada).",
    "en la placa el encapsulado es {0}, pero la pieza es {1}",
    "Placa → JLC",
    "Placas en el pedido",
    "Importación de BOM: {0} designadores.",
    "Líneas de BOM",
    "BOM, precios, sustitutos, capas",
    "abajo",
    "Inferior (vista desde abajo)",
    "Cobre inferior",
    "Pasta inferior (plantilla)",
    "Las hojas BOTTOM se imprimen vistas desde arriba — para la cara inferior ese ya es el espejo correcto.",
    "Cara inferior",
    "Cara inferior: componentes SMD",
    "Serigrafía inferior",
    "Máscara de soldadura inferior",
    "Máscara inferior (UV): aperturas en negro",
    "Vista inferior (lado de soldadura)",
    "abajo a la izquierda",
    "abajo a la derecha",
    "pieza en la cara inferior: comprobar la rotación en la vista previa de JLCPCB",
    "Curvatura y torsión máx. {0} % (placa con componentes SMD).",
    "Examinar…",
    "Crear paquete",
    "SMD voluminosos: electrolíticos, inductores de potencia, conectores SMD",
    "por prefijo del número",
    "por número de pieza",
    "por forma",
    "por valor",
    "Cancelar",
    "No se pueden copiar los archivos a:",
    "No se puede crear la carpeta:",
    "No se encuentra la carpeta del usuario.",
    "No se pudo instalar el complemento dmxON en:",
    "Condensadores",
    "Catálogo",
    "en el catálogo: {0} (comprobar el sufijo)",
    "Consultas al catálogo: {0}, método: {1}, sin respuesta: {2}.",
    "cátodo",
    "centro",
    "comprobar el pinout",
    "comprobar la escala",
    "Compruebe la escala con una regla: la barra al pie de cada hoja mide 50 mm, el contorno de la placa {0} mm.",
    "comprobar: {0}, pero el valor es {1}",
    "Revisado por",
    "comprobando",
    "Esquema eléctrico",
    "Esquema eléctrico en la documentación",
    "¿Vaciarla? «No» — crear una carpeta nueva con fecha.",
    "Empresa",
    "Compatibilidad",
    "hay un sustituto compatible {0} (no aplicado; active los sustitutos en los ajustes)",
    "Colocación de componentes",
    "Componentes",
    "componentes",
    "Patrón conductor según los datos Gerber {0} (RS-274X); posiciones de taladros según el archivo Excellon.",
    "Conectores",
    "Copiado",
    "el cobre sobresale {0} mm del contorno de la placa",
    "Capas de cobre",
    "Capas de cobre: {0}; cobre exterior acabado 35 µm (1 oz); estructura de capas según la tabla.",
    "No se permite copiar el código, modificarlo ni usarlo comercialmente.",
    "Coste",
    "CPL (pick & place)",
    "CPL en el centro de los pads si la huella no está verificada",
    "Elaborado por",
    "Cristales y resonadores",
    "Cliente",
    "Fecha de emisión",
    "Copia del diseño",
    "Copia del diseño (esquema y placa):",
    "No se escribió la copia del diseño: no hay archivo de placa.",
    "Designación",
    "Designador",
    "designador en la lista de exclusión",
    "Designadores",
    "Designadores y notas",
    "designaciones en los detalles {0}…{1}",
    "Diseñado por",
    "detalle",
    "Diagnóstico",
    "Diámetro, mm",
    "difiere",
    "Dimensiones, mm",
    "Diodos",
    "dmxON FabKit eliminado.",
    "atributo DNP / JLC_EXCLUDE",
    "No montar los componentes que no figuran en la lista de piezas {0}.",
    "No montar los componentes que no figuran en {0}.",
    "Lista de documentos",
    "N.º de documento",
    "Estado del documento",
    "Tipo de documento",
    "Documentación",
    "no encaja",
    "Hecho.",
    "Cajetín del plano (esta placa)",
    "planos, orden de soldadura, marcas",
    "Taladrado (metalizado y no metalizado)",
    "Guía de taladrado (vista superior)",
    "Mapa de taladros",
    "Taladrado",
    "esquema y placa EAGLE, STEP de la placa, toda la carpeta en la nube",
    "esquema y placa EAGLE, zip",
    "no se pudo leer el modelo de EasyEDA",
    "ENIG según IPC-4552B",
    "Cada capa por separado",
    "Excluido",
    "Tarifa de alimentador Extended, $",
    "Carga de Extended ({0})",
    "sobresale {0} mm del contorno — el fabricante lo recortará",
    "FabKit es gratuito. Si le ha ahorrado tiempo o dinero, apoye las nuevas versiones.",
    "Fabricar según GOST R 53429-2009, clase de precisión {0}; calidad según IPC-6012F, clase {1}; aceptación según IPC-A-600M.",
    "Fabricar según IPC-6012F, clase {0}; aceptabilidad según IPC-A-600M, clase {0}.",
    "Plano de fabricación",
    "Los campos también se pueden editar después, directamente en el HTML de la documentación.",
    "Archivo",
    "Los números del archivo tienen prioridad sobre los atributos. Lee «Download Selected Parts List» y cualquier CSV/XLSX con Designator y LCSC.",
    "Archivos",
    "Los archivos llevan los nombres que espera JLCPCB (Protel: GTL, GBL, G1…, GTS, GTP, GTO, GKO, XLN). Active y desactive capas a la izquierda.",
    "Archivos para JLCPCB",
    "Archivo…",
    "CI de paso fino (QFN, QFP, paso ≤ 0.65 mm)",
    "Primer uso",
    "Flux y pasta o soldadura por arrastre; revisar puentes con lupa. Pad central — aire caliente.",
    "Carpeta",
    "carpeta",
    "la huella difiere de JLC: algunos terminales quedan en parte fuera de los pads (hasta {0} mm)",
    "la huella no encaja",
    "la huella es la imagen especular del encapsulado de la pieza ({0})",
    "huella coincide",
    "la huella coincide por números de pin",
    "la huella coincide por forma — comprobar el pinout y la pieza complementaria",
    "huella no verificada",
    "huella: observaciones",
    "la huella {0} no encaja con el encapsulado {1}, desviación de hasta {2} mm",
    "la huella {0} no tiene pasta (tCream) — la plantilla no la aplicará, revisar la biblioteca",
    "huellas",
    "Huellas",
    "Huellas y orientación",
    "Formato",
    "encontradas",
    "Uso gratuito citando al autor.",
    "de atributos",
    "de atributos / importación",
    "Fusibles",
    "Origen en Fusion",
    "Gerber",
    "Gerber y taladrado para JLCPCB (zip + vistas previas de capas)",
    "Gerber para JLCPCB",
    "Capas Gerber y taladrado",
    "Gerber no exportado",
    "verde",
    "Manipular los dispositivos sensibles a electricidad estática según IEC 61340-5-1:2024.",
    "HASL (estaño-plomo)",
    "Taladros",
    "Pase el cursor para separar las capas",
    "Número de identificación",
    "Importar una BOM de JLCPCB terminada (opcional)",
    "BOM importada",
    "En la vista previa de JLCPCB, comprobar la rotación de las piezas de la sección «Atención».",
    "Inductores y ferritas",
    "Cobre interno {0}",
    "Instalar",
    "Instalación",
    "Instalación en Autodesk Fusion:",
    "Circuitos integrados",
    "Problema",
    "Pos.",
    "JLC no tiene modelo de huella",
    "el modelo de JLC no tiene pads",
    "BOM de JLCPCB",
    "catálogo JLCPCB",
    "El catálogo de JLCPCB no respondió",
    "Precios del catálogo JLCPCB en el momento de la exportación, para {0} placas, sin margen de pérdidas ni coste de placa y montaje. Cada pieza Extended única añade una tarifa de carga de alimentador ({1}).",
    "catálogo JLCPCB: desactivado",
    "catálogo JLCPCB: en línea",
    "Marca",
    "Marca: 1 — pin 1, K — cátodo; la flecha indica dónde está respecto al centro del cuerpo.",
    "Idioma",
    "Idioma",
    "Gran masa térmica: más calor; polaridad de los electrolíticos.",
    "Capa",
    "PDF de capas",
    "Capas",
    "Selección de piezas LCSC",
    "Atributos LCSC_PART escritos",
    "Atributos LCSC_PART escritos: {0}.",
    "HASL sin plomo",
    "Sin plomo, conforme a RoHS (Directiva 2011/65/UE).",
    "LED",
    "izquierda",
    "Propietario legal",
    "biblioteca",
    "Líneas sin precio en el catálogo: {0}.",
    "Lista de elementos",
    "Lote",
    "Comprobación de fabricabilidad",
    "Fabricante",
    "Documentación para la fabricación y el montaje del circuito impreso",
    "Masa",
    "coincide",
    "Coincidencia",
    "Tensión mín. de condensadores, V",
    "Taladro mín., mm",
    "taladro mín. de {0} mm, por debajo del estándar de 0.3 mm para 1–2 capas",
    "taladro mín. de {0} mm — estándar",
    "taladro mín. de {0} mm: válido para multicapa; los taladros de menos de 0.3 mm pueden encarecer el pedido",
    "Ancho mín. de pista, mm",
    "Respetar la polaridad de diodos y LED (marca del cátodo).",
    "Ancho mínimo de conductor {0} mm; taladro acabado mínimo {1} mm.",
    "ESPEJADO",
    "espejada",
    "mm",
    "Líneas más caras",
    "taladro de montaje / fiducial",
    "Nombre",
    "Necesario",
    "requieren atención",
    "Requieren atención",
    "No",
    "sin respuesta de EasyEDA",
    "sin respuesta de JLCPCB, número no verificado",
    "Sin observaciones.",
    "No se ha indicado la carpeta.",
    "sin pads (logotipo, gráfico)",
    "sin número",
    "sin sustituto: ninguna alternativa en stock tiene una huella compatible",
    "No hicieron falta sustitutos.",
    "no aplicado",
    "No exportado a BOM/CPL",
    "no encontrado",
    "no encontrado por valor; el atributo MPN {0} no se usó: el valor indica otra pieza",
    "no está en el catálogo de JLCPCB",
    "sin espejar",
    "Nota",
    "Notas",
    "Nada.",
    "Desplazamiento, mm",
    "Abrir la carpeta al terminar",
    "Pedido",
    "Código de pedido",
    "Pedido en JLCPCB",
    "Original",
    "OSP (conservante orgánico de soldabilidad)",
    "Otros CI y transistores (SOIC, SOT, TSSOP)",
    "Otros artículos",
    "Otros componentes",
    "Resto de SMD: 1206+, diodos, LED, cristales",
    "Grosor del cobre exterior",
    "Tolerancia del contorno ±{0} mm; cotas en milímetros.",
    "Salida",
    "Carpeta de salida",
    "Superposición",
    "Encapsulado",
    "no se encuentra la carpeta del paquete",
    "pads sin pasta (fiducial, puente, pad de contacto)",
    "Formato",
    "Papel: satinado/fotográfico o film de transferencia; plancha a 160–180 °C.",
    "parte",
    "Pieza",
    "N.º de pieza",
    "terminales de la pieza sin pad en la placa: {0}",
    "Número de pieza",
    "número tomado del atributo MPN {0}",
    "Piezas",
    "Coste de piezas (estimación)",
    "Lista de piezas",
    "piezas, estimación",
    "Placa",
    "Capas de la placa",
    "Opciones de pedido de la placa",
    "Parámetros de la placa para el formulario de pedido",
    "Número de pieza de la PCB",
    "Cantidad de placas",
    "Grosor de la placa, mm",
    "Placa: archivo",
    "PDF de la documentación (con Microsoft Edge)",
    "por placa",
    "Por placa",
    "fase 2: exportación de Fusion",
    "fase 2: el complemento dmxON exporta los Gerber",
    "pin 1",
    "Marcas de pin 1 y polaridad",
    "números de pin",
    "los números de pin no coinciden",
    "Colocación",
    "pieza polarizada girada {0}° según los números de pad 1/2 — las bibliotecas numeran de forma distinta los componentes de dos terminales, comprobar la marca de polaridad en la vista previa",
    "la polaridad no se deduce de la forma — comprobar en la vista previa de JLCPCB",
    "Preferir Basic/Preferred (sin tarifa de alimentador)",
    "Preparado con: {0}",
    "Imprimir en impresora láser al 100% («Tamaño real»). No usar nunca «Ajustar a la página».",
    "Placa de circuito impreso",
    "Producto",
    "Paquete de fabricación",
    "Informe de fabricación",
    "morado",
    "Función",
    "Cant.",
    "Motivo",
    "rojo",
    "Desig. ref.",
    "N.º ref.",
    "Designación de referencia",
    "Designaciones de referencia como en el esquema (GOST 2.710-81); un punto marca el pin 1 o el cátodo.",
    "Designaciones de referencia como en el esquema (códigos de letras según IEC 81346-2:2019); un punto marca el pin 1 o el cátodo.",
    "Relés",
    "Quitar",
    "Eliminar los restos de fundente tras soldar, salvo si se usa fundente no-clean.",
    "informe",
    "Informe",
    "consulta {0} de {1}",
    "Resistencias",
    "Tras instalar, reinicie Fusion una vez.",
    "Reinicie Fusion para quitar la pestaña dmxON.",
    "Reinicie Fusion: la pestaña dmxON aparece en los editores de placa y esquema, y {0} en Automation → Run ULP.",
    "Resultado",
    "Rev.",
    "derecha",
    "Rotación",
    "la corrección de rotación {0} del atributo o archivo se sustituyó por la calculada {1}",
    "Ejecute dmxON FabKit desde el editor de placas.",
    "Escala",
    "esquema",
    "Buscar en el catálogo de JLCPCB (en línea)",
    "buscando sustitutos",
    "ver plano",
    "forma",
    "la forma coincide pero los números de pin no — comprobar el pinout",
    "Proporción",
    "Comunes a todas las placas",
    "hoja",
    "Hoja",
    "Hojas",
    "Las hojas se generan a partir de los mismos Gerber que van a la fábrica: rellenos de cobre, separaciones y recortes son exactos. Los puntos blancos marcan los centros de los taladros.",
    "Serigrafía",
    "Tamaño",
    "Omitir designadores",
    "Pasivos pequeños (0201–0805)",
    "puente de soldadura / punto de prueba",
    "Máscara de soldadura",
    "Color de la máscara",
    "Máscara de soldadura: LPI según IPC-SM-840E, clase T, {0}, ambas caras; serigrafía con tinta no conductora, {1}.",
    "Suelde primero la cara con menos piezas y más ligeras.",
    "Orden de soldadura — paso {0} de {1}",
    "Orden de soldadura y marcas del pin 1 según {0}.",
    "Origen",
    "Especificación",
    "Fase",
    "Norma",
    "Stock",
    "stock {0} < necesario {1}",
    "en stock {0} de {1}",
    "Almacenar y hornear los dispositivos sensibles a la humedad según IPC/JEDEC J-STD-033D (MSL según J-STD-020F).",
    "sustituto",
    "Sustituto",
    "SUSTITUTO",
    "sustitutos",
    "Sustitutos",
    "Sustitutos (alternativas del catálogo JLCPCB)",
    "Apoye el proyecto",
    "Acabado superficial",
    "Acabado superficial: {0}; soldabilidad según J-STD-003D.",
    "Interruptores",
    "Fijar un pin, alinear con la marca del pin 1 y soldar el resto.",
    "La placa tiene {0} capas de cobre: en casa solo se hacen placas de doble cara — estas hojas cubren solo las capas exteriores (como referencia o para un prototipo simplificado).",
    "en la placa pone la versión {0}, el paquete es la versión {1}",
    "en la placa pone la versión {0}, el paquete es la versión {1}: corrija el texto o la versión en la pestaña Cajetín.",
    "el atributo REV del diseño es {0} y el paquete es la versión {1}: ejecute FabKit desde su ventana para guardar la versión en el diseño",
    "El complemento dmxON añade allí también el STEP de la placa con sus piezas y toda la carpeta del diseño en la nube (3D, planos, archivos).",
    "se instala el complemento dmxON: la pestaña <b>dmxON</b> aparece en los editores de placa y esquema — FabKit, JLC Rules, copia de la carpeta del diseño, actualizaciones desde GitHub",
    "El complemento dmxON se actualizó: reinicie Fusion para usar la nueva versión.",
    "las carpetas dmxON se añaden a las listas de ULP, reglas de diseño y CAM de Fusion — <b>{0}</b> también está en Automation → Run ULP; los ULP integrados se mantienen",
    "La pestaña dmxON ya funciona y {0} está actualizado; también está en Automation → Run ULP.",
    "La carpeta ya existe y no la creó FabKit:",
    "El paquete se crea en «{0}»: la versión se fija en la pestaña Cajetín y aparece en todos los nombres de archivo y cajetines; el paquete anterior de esta versión se reemplaza por completo.",
    "el proyecto se copia en <tt>{0}</tt>",
    "Espesor, mm",
    "Componentes pasantes (THT)",
    "componente pasante (THT desactivado)",
    "Componentes pasantes (THT) — al final",
    "Los THT al final, tras limpiar los SMD; los bajos antes que los altos.",
    "Cajetín",
    "Los campos del cuadro de rotulación se pueden editar aquí; después Ctrl+P → Guardar como PDF (márgenes: ninguno).",
    "Título, título complementario",
    "Transferencia de tóner 1:1",
    "Hojas para transferencia de tóner, escala 1:1",
    "Herramienta",
    "arriba",
    "Superior",
    "arriba / abajo",
    "Cobre superior",
    "Pasta superior (plantilla)",
    "Las hojas TOP ya están espejadas: tras transferir con la plancha, la imagen se lee correctamente en la placa.",
    "Cara superior",
    "Serigrafía superior",
    "Máscara de soldadura superior",
    "Máscara superior (UV): aperturas en negro",
    "Vista superior",
    "arriba a la izquierda",
    "arriba a la derecha",
    "Total",
    "ancho de pista desde {0} mm — en el límite de capacidad",
    "ancho de pista desde {0} mm — estándar",
    "ancho de pista de {0} mm, por debajo del mínimo de {1} mm",
    "Transformadores",
    "Transistores",
    "Pinzas y punta fina; fijar un lado y luego el otro.",
    "Tipo",
    "Precio unit.",
    "Se usa en el informe, en los parámetros del pedido y en la vista de la placa.",
    "valor",
    "Valor",
    "Verificar huellas con JLC; rotación y centro del CPL a partir de ellas",
    "Versión",
    "Versión (Rev.)",
    "Versión {0} guardada en el diseño (atributo REV).",
    "versión {0}: en los nombres de archivo y cajetines{1}",
    "Vista",
    "ATENCIÓN",
    "Qué va al BOM/CPL",
    "Qué crear",
    "Qué subir",
    "Dónde",
    "blanco",
    "Escribir los números en atributos LCSC_PART",
    "amarillo",
    "Sí",
    "Zona",
    "{0} aperturas · {1} líneas · {2} destellos",
    "{0} trazos de cobre de menos de 0.05 mm (gráfico, logotipo) no se fabricarán",
    "{0} archivos, {1} capas de cobre",
    "{0} no está en el catálogo de JLCPCB",
    "{0} está fuera del contorno de la placa",
    "{0} es de {1} V, se requieren {2} V",
    "{0} regiones",
    "{0} consultas mediante curl...",
    "{0} herramientas · {1} taladros",
    "{0}, pero el valor es {1}",
    "{0}; no hay sustituto por valor, se mantiene {1}"
};

string TR_DE[] = {
    " und auf der Platine",
    "100 % elektrische Prüfung aller Netze nach IPC-9252B.",
    "1:1-Blätter für Tonertransfer (PDF)",
    "A4-Dokumentation",
    "A4-Dokumentation für die Handbestückung",
    "Info",
    "Beide Seiten über die Bohrungen ausrichten (Blatt DRILL), bei Bedarf zuerst bohren.",
    "Bereits installiert — «Installieren» aktualisiert die Dateien.",
    "Für fehlende, nicht vorrätige oder nicht passende Bauteile werden Alternativen gesucht. Eine Alternative wird nur übernommen, wenn ihr Footprint aus der JLC-Bibliothek zu den Pads der Platine passt. Die günstigste für die gesamte Charge gewinnt.",
    "und CPL (Bestückungsdaten)",
    "Anode und Kathode",
    "übernommen",
    "Günstigere kompatible Ersatzteile für fehlende Teile einsetzen",
    "Freigegeben von",
    "Bestücken und löten nach IPC J-STD-001J, Klasse {0}; Abnahme nach IPC-A-610J, Klasse {0}.",
    "Bestückungs-BOM",
    "Bestückungszeichnung",
    "Montageanleitung",
    "Bestückungsseite",
    "Bestückungsvariante: nicht bestücken",
    "Bestückung (PCB Assembly): BOM",
    "Achtung",
    "Attribut",
    "Teilenummer im Attribut widerspricht dem Wert — neu auswählen",
    "Attribut {0} — nach Wert durch {1} ersetzt",
    "Design ins Paket sichern (05_BACKUP): Schaltplan und Platine; mit dem dmxON-Add-in das Platinen-STEP und der gesamte Cloud-Ordner",
    "Basismaterial",
    "Basismaterial: FR-4 nach IPC-4101F/21; Leiterplattendicke {0} mm ±10 %.",
    "Charge",
    "Batterien",
    "Stückliste (BOM)",
    "schwarz",
    "blau",
    "Blau — Pads der Platine, orange Kontur — Footprint aus der JLC-Bibliothek (EasyEDA) nach dem Abgleich. Kreuz — Footprint-Ursprung auf der Platine, oranger Kreis — Bauteilmitte bei JLC, die ins CPL geschrieben wird. Punkte markieren Pin 1. Drehung korrigiert bei {0} Teilen, Mitte bei {1}.",
    "Blau — Pads der Platine, orange — Footprint des Ersatzteils.",
    "Platine",
    "Platinenkontur",
    "Platinenkontur, Pads, Gehäuse und Bezeichner. Der rote Punkt markiert Pin 1 oder die Kathode. Die Unterseite ist von der Lötseite aus gesehen (gespiegelt).",
    "Gehäuse auf der Platine {0}, das Bauteil ist aber {1}",
    "Platine → JLC",
    "Platinen in der Bestellung",
    "BOM-Import: {0} Bezeichner.",
    "BOM-Zeilen",
    "BOM, Preise, Ersatzteile, Lagen",
    "unten",
    "Unterseite (von unten gesehen)",
    "Kupfer unten",
    "Lotpaste unten (Schablone)",
    "BOTTOM-Blätter sind von oben gesehen gedruckt — für die Unterseite ist das bereits die richtige Spiegelung.",
    "Unterseite",
    "Unterseite: SMD-Bauteile",
    "Bestückungsdruck unten",
    "Lötstoppmaske unten",
    "Lötstoppmaske unten (UV): Öffnungen schwarz",
    "Unteransicht (Lötseite)",
    "unten links",
    "unten rechts",
    "Bauteil auf der Unterseite: Drehung in der JLCPCB-Vorschau prüfen",
    "Durchbiegung und Verwindung max. {0} % (Leiterplatte mit SMD-Bauteilen).",
    "Durchsuchen…",
    "Paket erstellen",
    "Große SMD: Elkos, Leistungsdrosseln, SMD-Steckverbinder",
    "nach Nummernpräfix",
    "nach Teilenummer",
    "nach Form",
    "nach Wert",
    "Abbrechen",
    "Dateien können nicht kopiert werden nach:",
    "Ordner kann nicht erstellt werden:",
    "Benutzerordner nicht gefunden.",
    "Das dmxON-Add-in konnte nicht installiert werden in:",
    "Kondensatoren",
    "Katalog",
    "im Katalog: {0} (Suffix prüfen)",
    "Katalogabfragen: {0}, Methode: {1}, ohne Antwort: {2}.",
    "Kathode",
    "Mitte",
    "Pinbelegung prüfen",
    "Maßstab prüfen",
    "Maßstab mit einem Lineal prüfen: Der Balken unten auf jedem Blatt ist 50 mm lang, die Platinenkontur {0} mm.",
    "prüfen: {0}, aber der Wert ist {1}",
    "Geprüft von",
    "Prüfung",
    "Stromlaufplan",
    "Stromlaufplan in der Dokumentation",
    "Leeren? «Nein» — einen neuen Ordner mit Datum anlegen.",
    "Firma",
    "Kompatibilität",
    "kompatibles Ersatzteil {0} verfügbar (nicht übernommen, Ersatzteile in den Einstellungen aktivieren)",
    "Bauteilplatzierung",
    "Bauteile",
    "Bauteile",
    "Leiterbild nach Gerber-Daten {0} (RS-274X); Bohrpositionen nach der Excellon-Datei.",
    "Steckverbinder",
    "Kopiert",
    "Kupfer ragt {0} mm über die Platinenkontur hinaus",
    "Kupferlagen",
    "Kupferlagen: {0}; Außenkupfer fertig 35 µm (1 oz); Lagenaufbau nach Tabelle.",
    "Kopieren des Codes, Änderung und kommerzielle Nutzung sind nicht gestattet.",
    "Kosten",
    "CPL (Bestückungsdaten)",
    "CPL in der Pad-Mitte, wenn der Footprint nicht geprüft ist",
    "Erstellt von",
    "Quarze und Resonatoren",
    "Kunde",
    "Ausgabedatum",
    "Design-Sicherung",
    "Design-Sicherung (Schaltplan und Platine):",
    "Design-Sicherung nicht geschrieben — keine Platinendatei.",
    "Bezeichnung",
    "Bezeichner",
    "Bezeichner in der Ausschlussliste",
    "Bezeichner",
    "Bezeichner und Hinweise",
    "Kennzeichen in den Einzelheiten {0}…{1}",
    "Entworfen von",
    "Einzelheit",
    "Diagnose",
    "Durchmesser, mm",
    "weicht ab",
    "Abmessungen, mm",
    "Dioden",
    "dmxON FabKit entfernt.",
    "Attribut DNP / JLC_EXCLUDE",
    "Bauteile, die nicht in der Stückliste {0} stehen, nicht bestücken.",
    "Bauteile, die nicht in {0} stehen, nicht bestücken.",
    "Dokumentenliste",
    "Dokument-Nr.",
    "Dokumentstatus",
    "Dokumentart",
    "Dokumentation",
    "passt nicht",
    "Fertig.",
    "Schriftfeld der Zeichnung (diese Platine)",
    "Zeichnungen, Lötreihenfolge, Markierungen",
    "Bohrungen (durchkontaktiert und nicht)",
    "Bohrplan (Draufsicht)",
    "Bohrplan",
    "Bohrungen",
    "EAGLE-Schaltplan und -Platine, Platinen-STEP, gesamter Cloud-Ordner",
    "EAGLE-Schaltplan und -Platine, zip",
    "EasyEDA-Modell nicht lesbar",
    "ENIG nach IPC-4552B",
    "Jede Lage einzeln",
    "Ausgeschlossen",
    "Feeder-Gebühr Extended, $",
    "Extended-Rüstgebühr ({0})",
    "ragt {0} mm über die Kontur hinaus — der Hersteller schneidet es ab",
    "FabKit ist kostenlos. Wenn es Ihnen Zeit oder Geld gespart hat, unterstützen Sie bitte neue Versionen.",
    "Fertigung nach GOST R 53429-2009, Genauigkeitsklasse {0}; Qualität nach IPC-6012F, Klasse {1}; Abnahme nach IPC-A-600M.",
    "Fertigung nach IPC-6012F, Klasse {0}; Annehmbarkeit nach IPC-A-600M, Klasse {0}.",
    "Fertigungszeichnung",
    "Die Felder lassen sich auch später direkt im HTML der Dokumentation bearbeiten.",
    "Datei",
    "Nummern aus der Datei haben Vorrang vor Attributen. Liest «Download Selected Parts List» und jede CSV/XLSX mit Designator und LCSC.",
    "Dateien",
    "Die Dateien sind so benannt, wie JLCPCB sie erwartet (Protel: GTL, GBL, G1…, GTS, GTP, GTO, GKO, XLN). Lagen links ein- und ausschalten.",
    "Dateien für JLCPCB",
    "Datei…",
    "ICs mit feinem Raster (QFN, QFP, Raster ≤ 0.65 mm)",
    "Erstverwendung",
    "Flussmittel und Paste oder Schlepplöten; auf Brücken prüfen. Thermal-Pad — Heißluft.",
    "Ordner",
    "Ordner",
    "Footprint weicht von JLC ab: einige Anschlüsse teils außerhalb der Pads (bis {0} mm)",
    "Footprint passt nicht",
    "Footprint ist ein Spiegelbild des Bauteilgehäuses ({0})",
    "Footprint passt",
    "Footprint passt nach Pinnummern",
    "Footprint passt nach Form — Pinbelegung und Gegenstück prüfen",
    "Footprint nicht geprüft",
    "Footprint: Hinweise",
    "Footprint {0} passt nicht zum Gehäuse {1}, Abweichung bis {2} mm",
    "Footprint {0} hat keine Paste (tCream) — die Schablone trägt keine Paste auf, Bibliothek prüfen",
    "Footprints",
    "Footprints",
    "Footprints und Ausrichtung",
    "Format",
    "gefunden",
    "Kostenlose Nutzung mit Namensnennung.",
    "aus Attributen",
    "aus Attributen / Import",
    "Sicherungen",
    "Fusion-Quelle",
    "Gerber",
    "Gerber und Bohrdaten für JLCPCB (Zip + Lagenvorschau)",
    "Gerber für JLCPCB",
    "Gerber-Lagen und Bohrungen",
    "Gerber wurde nicht exportiert",
    "grün",
    "Elektrostatisch gefährdete Bauelemente nach IEC 61340-5-1:2024 handhaben.",
    "HASL (Zinn-Blei)",
    "Bohrungen",
    "Mauszeiger darüber — die Lagen fächern sich auf",
    "Sachnummer",
    "Fertige JLCPCB-BOM importieren (optional)",
    "importierte BOM",
    "In der JLCPCB-Vorschau die Drehung der unter «Achtung» aufgeführten Teile prüfen.",
    "Induktivitäten und Ferrite",
    "Kupfer innen {0}",
    "Installieren",
    "Installation",
    "Installation in Autodesk Fusion:",
    "Integrierte Schaltungen",
    "Problem",
    "Pos.",
    "JLC hat kein Footprint-Modell",
    "JLC-Modell hat keine Pads",
    "JLCPCB-BOM",
    "JLCPCB-Katalog",
    "JLCPCB-Katalog hat nicht geantwortet",
    "JLCPCB-Katalogpreise zum Exportzeitpunkt für {0} Platinen, ohne Ausschusszuschlag, Platinen- und Bestückungskosten. Jedes einzelne Extended-Teil kostet zusätzlich eine Feeder-Rüstgebühr ({1}).",
    "JLCPCB-Katalog: aus",
    "JLCPCB-Katalog: online",
    "Markierung",
    "Markierung: 1 — Pin 1, K — Kathode; der Pfeil zeigt, wo er von der Gehäusemitte aus liegt.",
    "Spr.",
    "Sprache",
    "Große Wärmekapazität: mehr Hitze; Polung der Elkos beachten.",
    "Lage",
    "PDFs der Lagen",
    "Lagen",
    "LCSC-Teileauswahl",
    "LCSC_PART-Attribute geschrieben",
    "LCSC_PART-Attribute geschrieben: {0}.",
    "bleifreies HASL",
    "Bleifrei, RoHS-konform (Richtlinie 2011/65/EU).",
    "LEDs",
    "links",
    "Rechtlicher Eigentümer",
    "Bibliothek",
    "Zeilen ohne Katalogpreis: {0}.",
    "Elementeliste",
    "Los",
    "Fertigbarkeitsprüfung",
    "Hersteller",
    "Dokumentation für Fertigung und Bestückung der Baugruppe",
    "Masse",
    "passt",
    "Abgleich nach",
    "Min. Kondensatorspannung, V",
    "Min. Bohrdurchmesser, mm",
    "min. Bohrung {0} mm liegt unter dem Standard von 0.3 mm für 1–2 Lagen",
    "min. Bohrung {0} mm — Standard",
    "min. Bohrung {0} mm: für Mehrlagen zulässig, Bohrungen unter 0.3 mm können den Preis erhöhen",
    "Min. Leiterbahnbreite, mm",
    "Polung von Dioden und LEDs beachten (Kathodenmarkierung).",
    "Mindestleiterbreite {0} mm; kleinste fertige Bohrung {1} mm.",
    "GESPIEGELT",
    "gespiegelt",
    "mm",
    "Teuerste Zeilen",
    "Befestigungsloch / Passermarke",
    "Benennung",
    "Bedarf",
    "brauchen Aufmerksamkeit",
    "Achtung erforderlich",
    "Nein",
    "keine Antwort von EasyEDA",
    "keine Antwort von JLCPCB, Teilenummer nicht geprüft",
    "Keine Hinweise.",
    "Kein Ausgabeordner angegeben.",
    "keine Pads (Logo, Grafik)",
    "ohne Teilenummer",
    "kein Ersatz: keine vorrätige Alternative hat einen kompatiblen Footprint",
    "Keine Ersatzteile nötig.",
    "nicht übernommen",
    "Nicht in BOM/CPL exportiert",
    "nicht gefunden",
    "nach Wert nicht gefunden; MPN-Attribut {0} nicht verwendet: der Wert verweist auf ein anderes Teil",
    "nicht im JLCPCB-Katalog",
    "nicht gespiegelt",
    "Bemerkung",
    "Anmerkungen",
    "Nichts.",
    "Versatz, mm",
    "Ordner nach Abschluss öffnen",
    "Bestellung",
    "Bestellcode",
    "Bestellung bei JLCPCB",
    "Original",
    "OSP (organischer Lötbarkeitsschutz)",
    "Sonstige ICs und Transistoren (SOIC, SOT, TSSOP)",
    "Sonstige Teile",
    "Sonstige Bauteile",
    "Übrige SMD: 1206+, Dioden, LEDs, Quarze",
    "Kupferstärke außen",
    "Konturtoleranz ±{0} mm; Maße in Millimetern.",
    "Ausgabe",
    "Ausgabeordner",
    "Überlagerung",
    "Gehäuse",
    "Paketordner nicht gefunden",
    "Pads ohne Paste (Passermarke, Brücke, Kontaktfläche)",
    "Blattgröße",
    "Papier: Glanz-/Fotopapier oder Transferfolie; Bügeleisen 160–180 °C.",
    "Teil",
    "Bauteil",
    "Teilenr.",
    "Bauteilanschlüsse ohne Pad auf der Platine: {0}",
    "Teilenummer",
    "Teilenummer aus MPN-Attribut {0} übernommen",
    "Bauteile",
    "Bauteilkosten (Schätzung)",
    "Stückliste",
    "Bauteile, Schätzung",
    "Platine",
    "Platinenlagen",
    "Bestelloptionen der Platine",
    "Platinenparameter für das Bestellformular",
    "Sachnummer der Leiterplatte",
    "Anzahl Platinen",
    "Platinendicke, mm",
    "Platine: Archiv",
    "PDF der Dokumentation (über Microsoft Edge)",
    "pro Platine",
    "Pro Platine",
    "Phase 2: Fusion-Export",
    "Phase 2: Das dmxON-Add-in exportiert die Gerber-Dateien",
    "Pin 1",
    "Pin-1- und Polaritätsmarkierungen",
    "Pinnummern",
    "Pinnummern stimmen nicht überein",
    "Platzierung",
    "gepoltes Bauteil um {0}° gedreht nach Padnummern 1/2 — zweipolige Bibliotheken nummerieren Pads unterschiedlich, Polaritätsmarkierung in der Vorschau prüfen",
    "Polarität lässt sich aus der Form nicht ableiten — in der JLCPCB-Vorschau prüfen",
    "Basic/Preferred bevorzugen (ohne Feeder-Gebühr)",
    "Erstellt mit: {0}",
    "Mit einem Laserdrucker in 100% («Tatsächliche Größe») drucken. Niemals «An Seite anpassen» verwenden.",
    "Leiterplatte",
    "Produkt",
    "Fertigungspaket",
    "Fertigungsbericht",
    "violett",
    "Zweck",
    "Anz.",
    "Grund",
    "rot",
    "Ref.-Kennz.",
    "Ref.-Nr.",
    "Referenzkennzeichen",
    "Referenzkennzeichen wie im Schaltplan (GOST 2.710-81); ein Punkt markiert Pin 1 oder die Katode.",
    "Referenzkennzeichen wie im Schaltplan (Kennbuchstaben nach IEC 81346-2:2019); ein Punkt markiert Pin 1 oder die Katode.",
    "Relais",
    "Entfernen",
    "Flussmittelrückstände nach dem Löten entfernen, außer bei No-Clean-Flussmittel.",
    "Bericht",
    "Bericht",
    "Anfrage {0} von {1}",
    "Widerstände",
    "Nach der Installation Fusion einmal neu starten.",
    "Fusion neu starten, um den Reiter dmxON zu entfernen.",
    "Fusion neu starten — der Reiter dmxON erscheint im Platinen- und Schaltplan-Editor, {0} unter Automation → Run ULP.",
    "Ergebnis",
    "Rev.",
    "rechts",
    "Drehung",
    "Drehkorrektur {0} aus Attribut/Datei durch berechnete {1} ersetzt",
    "dmxON FabKit im Board-Editor starten.",
    "Maßstab",
    "Schaltplan",
    "Im JLCPCB-Katalog suchen (online)",
    "Ersatzteilsuche",
    "siehe Zeichnung",
    "Form",
    "Form passt, Pinnummern nicht — Pinbelegung prüfen",
    "Anteil",
    "Für alle Platinen",
    "Blatt",
    "Blatt",
    "Blätter",
    "Die Blätter entstehen aus denselben Gerber-Dateien wie für die Fertigung: Kupferflächen, Abstände und Aussparungen sind exakt. Weiße Punkte markieren die Bohrmitten.",
    "Bestückungsdruck",
    "Größe",
    "Bezeichner auslassen",
    "Kleine passive Bauteile (0201–0805)",
    "Lötbrücke / Testpunkt",
    "Lötstoppmaske",
    "Farbe der Lötstoppmaske",
    "Lötstopplack: LPI nach IPC-SM-840E, Klasse T, {0}, beidseitig; Bestückungsdruck in nichtleitender Farbe, {1}.",
    "Zuerst die Seite mit weniger und leichteren Bauteilen löten.",
    "Lötreihenfolge — Schritt {0} von {1}",
    "Lötreihenfolge und Pin-1-Kennzeichnung nach {0}.",
    "Quelle",
    "Spezifikation",
    "Stufe",
    "Norm",
    "Lager",
    "Lager {0} < benötigt {1}",
    "Lager {0} von {1}",
    "Feuchteempfindliche Bauteile nach IPC/JEDEC J-STD-033D lagern und trocknen (MSL nach J-STD-020F).",
    "Ersatzteil",
    "Ersatzteil",
    "ERSATZ",
    "Ersatzteile",
    "Ersatzteile",
    "Ersatzteile (Alternativen aus dem JLCPCB-Katalog)",
    "Projekt unterstützen",
    "Oberfläche",
    "Oberfläche: {0}; Lötbarkeit nach J-STD-003D.",
    "Schalter",
    "Einen Pin anheften, an der Pin-1-Markierung ausrichten, dann den Rest löten.",
    "Die Platine hat {0} Kupferlagen: zu Hause lassen sich nur doppelseitige Platinen herstellen — diese Blätter decken nur die Außenlagen ab (zur Orientierung oder für einen vereinfachten Prototyp).",
    "auf der Platine steht Version {0}, das Paket ist Version {1}",
    "auf der Platine steht Version {0}, das Paket ist Version {1}: Text oder Version auf dem Reiter Schriftfeld korrigieren.",
    "das Design-Attribut REV ist {0}, das Paket ist Version {1}: FabKit über sein Fenster starten, um die Version im Design zu speichern",
    "Das dmxON-Add-in legt dort auch das Platinen-STEP mit Bauteilen und den gesamten Cloud-Designordner ab (3D, Zeichnungen, Dateien).",
    "das dmxON-Add-in wird installiert: Der Reiter <b>dmxON</b> erscheint im Platinen- und Schaltplan-Editor — FabKit, JLC Rules, Sicherung des Designordners, Updates von GitHub",
    "Das dmxON-Add-in wurde aktualisiert — Fusion neu starten, um die neue Version zu nutzen.",
    "die dmxON-Ordner werden zu den ULP-, Designregel- und CAM-Listen von Fusion hinzugefügt — <b>{0}</b> steht auch unter Automation → Run ULP; die eingebauten ULPs bleiben",
    "Der Reiter dmxON läuft bereits und {0} ist aktualisiert — es steht auch unter Automation → Run ULP.",
    "Der Ordner existiert und wurde nicht von FabKit angelegt:",
    "Das Paket landet in «{0}»: Die Version wird auf dem Reiter Schriftfeld gesetzt und steht in allen Dateinamen und Schriftfeldern; ein früheres Paket dieser Version wird vollständig ersetzt.",
    "das Projekt wird nach <tt>{0}</tt> kopiert",
    "Dicke, mm",
    "Bedrahtete Bauteile (THT)",
    "bedrahtetes Bauteil (THT ausgeschaltet)",
    "Bedrahtete Bauteile (THT) — zuletzt",
    "THT-Teile zuletzt, nach dem Reinigen der SMD; niedrige vor hohen.",
    "Schriftfeld",
    "Die Schriftfeld-Felder sind hier bearbeitbar, dann Strg+P → Als PDF speichern (Ränder: keine).",
    "Titel, Ergänzungstitel",
    "Tonertransfer 1:1",
    "Blätter für Tonertransfer, Maßstab 1:1",
    "Werkzeug",
    "oben",
    "Oberseite",
    "oben / unten",
    "Kupfer oben",
    "Lotpaste oben (Schablone)",
    "TOP-Blätter sind bereits gespiegelt: nach dem Aufbügeln ist das Bild auf der Platine richtig lesbar.",
    "Oberseite",
    "Bestückungsdruck oben",
    "Lötstoppmaske oben",
    "Lötstoppmaske oben (UV): Öffnungen schwarz",
    "Draufsicht",
    "oben links",
    "oben rechts",
    "Gesamt",
    "Leiterbahnbreite ab {0} mm — an der Fertigungsgrenze",
    "Leiterbahnbreite ab {0} mm — Standard",
    "Leiterbahnbreite {0} mm liegt unter dem Minimum von {1} mm",
    "Transformatoren",
    "Transistoren",
    "Pinzette und feine Spitze; erst eine Seite anheften, dann die andere.",
    "Typ",
    "Stückpreis",
    "Wird im Bericht, in den Bestellparametern und in der Platinenansicht verwendet.",
    "Wert",
    "Wert",
    "Footprints mit JLC abgleichen; Drehung und Mitte im CPL danach",
    "Version",
    "Version (Rev.)",
    "Version {0} im Design gespeichert (Attribut REV).",
    "Version {0} — in Dateinamen und Schriftfeldern{1}",
    "Ansicht",
    "ACHTUNG",
    "Was in BOM/CPL kommt",
    "Was erstellen",
    "Was hochladen",
    "Wohin",
    "weiß",
    "Teilenummern in LCSC_PART-Attribute schreiben",
    "gelb",
    "Ja",
    "Zone",
    "{0} Blenden · {1} Linien · {2} Blitze",
    "{0} Kupferstriche dünner als 0.05 mm (Grafik, Logo) werden nicht gefertigt",
    "{0} Dateien, {1} Kupferlagen",
    "{0} ist nicht im JLCPCB-Katalog",
    "{0} liegt außerhalb der Platinenkontur",
    "{0} ist für {1} V ausgelegt, {2} V erforderlich",
    "{0} Regionen",
    "{0} Anfragen über curl...",
    "{0} Werkzeuge · {1} Bohrungen",
    "{0}, aber der Wert ist {1}",
    "{0}; kein Ersatz nach Wert gefunden, {1} beibehalten"
};

string TR_PL[] = {
    " i na płytce",
    "100 % test elektryczny wszystkich sieci wg IPC-9252B.",
    "Arkusze 1:1 do termotransferu (PDF)",
    "Dokumentacja A4",
    "Dokumentacja A4 do montażu ręcznego",
    "O programie",
    "Obie strony wyrównaj według otworów (arkusz DRILL); w razie potrzeby najpierw wywierć.",
    "Już zainstalowano — «Zainstaluj» zaktualizuje pliki.",
    "Dla części brakujących, niedostępnych w magazynie lub z niepasującą obudową szukane są zamienniki. Zamiennik jest przyjmowany tylko wtedy, gdy jego footprint z biblioteki JLC pasuje do padów płytki. Wygrywa najtańszy dla całej partii.",
    "i CPL (pick & place)",
    "anoda i katoda",
    "zastosowany",
    "Stosuj tańsze zgodne zamienniki brakujących części",
    "Zatwierdził",
    "Montaż i lutowanie wg IPC J-STD-001J, klasa {0}; odbiór wg IPC-A-610J, klasa {0}.",
    "BOM do montażu",
    "Rysunek montażowy",
    "Instrukcja montażu",
    "Strona montażu",
    "wariant montażu: nie montować",
    "Montaż (PCB Assembly): BOM",
    "Uwaga",
    "atrybut",
    "Numer w atrybucie nie zgadza się z wartością — dobierz ponownie",
    "atrybut {0} — zastąpiony przez {1} według wartości",
    "Kopia projektu w pakiecie (05_BACKUP): schemat i płytka; z dodatkiem dmxON — STEP płytki i cały folder z chmury",
    "Materiał bazowy",
    "Materiał podłoża: FR-4 wg IPC-4101F/21; grubość płytki {0} mm ±10 %.",
    "Partia",
    "Baterie",
    "Wykaz elementów (BOM)",
    "czarny",
    "niebieski",
    "Niebieskie — pady płytki, pomarańczowy obrys — footprint z biblioteki JLC (EasyEDA) po dopasowaniu. Krzyżyk — początek footprintu na płytce, pomarańczowe kółko — środek części JLC zapisywany do CPL. Kropki oznaczają pin 1. Poprawiono obrót części: {0}, środek: {1}.",
    "Niebieskie — pady płytki, pomarańczowe — footprint zamiennika.",
    "Płytka",
    "Obrys płytki",
    "Obrys płytki, pady, obudowy i oznaczenia. Czerwona kropka oznacza pin 1 lub katodę. Strona dolna pokazana od strony lutowania (lustrzanie).",
    "na płytce obudowa {0}, a część to {1}",
    "Płytka → JLC",
    "Płytek w zamówieniu",
    "Import BOM, oznaczeń: {0}.",
    "Pozycje BOM",
    "BOM, ceny, zamienniki, warstwy",
    "na dole",
    "Spód (widok od dołu)",
    "Miedź dolna",
    "Pasta dolna (szablon)",
    "Arkusze BOTTOM są drukowane w widoku z góry — dla strony dolnej to właśnie właściwe lustro.",
    "Strona dolna",
    "Strona dolna: elementy SMD",
    "Opisy (sitodruk) dolne",
    "Maska lutownicza dolna",
    "Maska dolna (UV): otwarcia czarne",
    "Widok z dołu (strona lutowania)",
    "na dole po lewej",
    "na dole po prawej",
    "część na stronie dolnej: sprawdź obrót w podglądzie JLCPCB",
    "Wygięcie i skręcenie maks. {0} % (płytka z elementami SMD).",
    "Przeglądaj…",
    "Utwórz pakiet",
    "Duże SMD: elektrolity, dławiki mocy, złącza SMD",
    "wg początku numeru",
    "wg numeru części",
    "wg kształtu",
    "wg wartości",
    "Anuluj",
    "Nie można skopiować plików do:",
    "Nie można utworzyć folderu:",
    "Nie znaleziono folderu użytkownika.",
    "Nie udało się zainstalować dodatku dmxON w:",
    "Kondensatory",
    "Katalog",
    "w katalogu: {0} (sprawdź sufiks)",
    "Zapytania do katalogów: {0}, metoda: {1}, bez odpowiedzi: {2}.",
    "katoda",
    "środek",
    "sprawdź wyprowadzenia",
    "sprawdź skalę",
    "Sprawdź skalę linijką: pasek na dole arkusza ma 50 mm, obrys płytki {0} mm.",
    "sprawdź: {0}, a wartość to {1}",
    "Sprawdził",
    "sprawdzanie",
    "Schemat ideowy",
    "Schemat ideowy w dokumentacji",
    "Wyczyścić go? «Nie» — utwórz nowy folder z datą.",
    "Firma",
    "Zgodność",
    "dostępny zgodny zamiennik {0} (nie zastosowany, włącz zamienniki w ustawieniach)",
    "Rozmieszczenie elementów",
    "Elementy",
    "elementy",
    "Mozaika przewodząca wg danych Gerber {0} (RS-274X); położenie otworów wg pliku Excellon.",
    "Złącza",
    "Kopiował",
    "miedź wychodzi {0} mm poza obrys płytki",
    "Warstwy miedzi",
    "Warstwy miedzi: {0}; miedź zewnętrzna po obróbce 35 µm (1 oz); układ warstw wg tabeli.",
    "Kopiowanie kodu, modyfikacja i użycie komercyjne są zabronione.",
    "Koszt",
    "CPL (pick & place)",
    "CPL w środku padów, gdy footprint nie jest sprawdzony",
    "Opracował",
    "Kwarce i rezonatory",
    "Klient",
    "Data wydania",
    "Kopia projektu",
    "Kopia projektu (schemat i płytka):",
    "Nie zapisano kopii projektu — brak pliku płytki.",
    "Oznaczenie",
    "Oznaczenie",
    "oznaczenie z listy wykluczeń",
    "Oznaczenia",
    "Oznaczenia i uwagi",
    "oznaczenia na szczegółach {0}…{1}",
    "Projektował",
    "szczegół",
    "Diagnostyka",
    "Średnica, mm",
    "różni się",
    "Wymiary, mm",
    "Diody",
    "dmxON FabKit usunięty.",
    "atrybut DNP / JLC_EXCLUDE",
    "Nie montować elementów nieujętych w wykazie części {0}.",
    "Nie montować elementów nieujętych w {0}.",
    "Wykaz dokumentów",
    "Nr dokumentu",
    "Status dokumentu",
    "Rodzaj dokumentu",
    "Dokumentacja",
    "nie pasuje",
    "Gotowe.",
    "Tabliczka rysunku (ta płytka)",
    "rysunki, kolejność lutowania, klucze",
    "Wiercenie (metalizowane i niemetalizowane)",
    "Mapa wiercenia (widok z góry)",
    "Mapa otworów",
    "Wiercenie",
    "schemat i płytka EAGLE, STEP płytki, cały folder z chmury",
    "schemat i płytka EAGLE, zip",
    "nie udało się odczytać modelu EasyEDA",
    "ENIG wg IPC-4552B",
    "Każda warstwa osobno",
    "Pominięte",
    "Opłata za podajnik Extended, $",
    "Załadunek Extended ({0})",
    "wychodzi {0} mm poza obrys — producent to przytnie",
    "FabKit jest darmowy. Jeśli zaoszczędził Ci czas lub pieniądze, wesprzyj nowe wersje.",
    "Wykonać wg GOST R 53429-2009, klasa dokładności {0}; jakość wg IPC-6012F, klasa {1}; odbiór wg IPC-A-600M.",
    "Wykonać wg IPC-6012F, klasa {0}; akceptowalność wg IPC-A-600M, klasa {0}.",
    "Rysunek wykonawczy",
    "Pola można też poprawić później, bezpośrednio w HTML dokumentacji.",
    "Plik",
    "Numery z pliku mają pierwszeństwo przed atrybutami. Czyta «Download Selected Parts List» i dowolny CSV/XLSX z kolumnami Designator i LCSC.",
    "Pliki",
    "Pliki mają nazwy, jakich oczekuje JLCPCB (Protel: GTL, GBL, G1…, GTS, GTP, GTO, GKO, XLN). Warstwy włączasz i wyłączasz po lewej.",
    "Pliki dla JLCPCB",
    "Plik…",
    "Układy o drobnym rastrze (QFN, QFP, raster ≤ 0.65 mm)",
    "Pierwsze zastosowanie",
    "Topnik i pasta lub lutowanie przeciąganiem; sprawdź mostki pod lupą. Pad centralny — gorące powietrze.",
    "Folder",
    "folder",
    "footprint różni się od JLC: część wyprowadzeń częściowo poza padami (do {0} mm)",
    "footprint nie pasuje",
    "footprint jest lustrzanym odbiciem obudowy części ({0})",
    "footprint zgodny",
    "footprint zgodny wg numerów pinów",
    "footprint zgodny wg kształtu — sprawdź wyprowadzenia i część współpracującą",
    "footprint niesprawdzony",
    "footprint: uwagi",
    "footprint {0} nie pasuje do obudowy {1}, odchyłka do {2} mm",
    "footprint {0} nie ma pasty (tCream) — szablon jej nie nałoży, sprawdź bibliotekę",
    "footprinty",
    "Footprinty",
    "Footprinty i orientacja",
    "Format",
    "znalezione",
    "Bezpłatne użycie z podaniem autora.",
    "z atrybutów",
    "z atrybutów / importu",
    "Bezpieczniki",
    "Plik źródłowy Fusion",
    "Gerber",
    "Gerber i wiercenie dla JLCPCB (zip + podglądy warstw)",
    "Gerber dla JLCPCB",
    "Warstwy Gerber i wiercenie",
    "Gerber nie został wyeksportowany",
    "zielony",
    "Z elementami wrażliwymi na ładunki elektrostatyczne postępować wg IEC 61340-5-1:2024.",
    "HASL (cyna-ołów)",
    "Otwory",
    "Najedź kursorem — warstwy się rozsuną",
    "Numer identyfikacyjny",
    "Import gotowej BOM JLCPCB (opcjonalnie)",
    "import BOM",
    "W podglądzie JLCPCB sprawdź obrót części z sekcji «Uwaga».",
    "Dławiki i ferryty",
    "Miedź wewnętrzna {0}",
    "Zainstaluj",
    "Instalacja",
    "Instalacja w Autodesk Fusion:",
    "Układy scalone",
    "Problem",
    "Poz.",
    "JLC nie ma modelu footprintu",
    "model JLC nie ma padów",
    "BOM JLCPCB",
    "katalog JLCPCB",
    "Katalog JLCPCB nie odpowiedział",
    "Ceny katalogu JLCPCB w chwili eksportu, płytek w zamówieniu: {0}; bez zapasu na straty, bez kosztu płytki i montażu. Każda unikalna część Extended dodaje opłatę za załadunek podajnika ({1}).",
    "katalog JLCPCB: wyłączony",
    "katalog JLCPCB: online",
    "Klucz",
    "Klucz: 1 — pin 1, K — katoda; strzałka pokazuje, gdzie leży względem środka obudowy.",
    "Jęz.",
    "Język",
    "Duża pojemność cieplna: mocniej grzać; polaryzacja elektrolitów.",
    "Warstwa",
    "PDF warstw",
    "Warstwy",
    "Dobór części LCSC",
    "Zapisane atrybuty LCSC_PART",
    "Zapisane atrybuty LCSC_PART: {0}.",
    "HASL bezołowiowy",
    "Bezołowiowe, zgodne z RoHS (dyrektywa 2011/65/UE).",
    "Diody LED",
    "po lewej",
    "Właściciel prawny",
    "biblioteka",
    "Pozycje bez ceny w katalogu: {0}.",
    "Wykaz elementów",
    "Partia",
    "Kontrola wykonalności",
    "Producent",
    "Dokumentacja do produkcji i montażu zespołu",
    "Masa",
    "zgodny",
    "Dopasowanie",
    "Min. napięcie kondensatorów, V",
    "Min. otwór, mm",
    "min. otwór {0} mm jest mniejszy od standardowych 0.3 mm dla 1–2 warstw",
    "min. otwór {0} mm — standard",
    "min. otwór {0} mm: dopuszczalny dla wielowarstwowych, otwory poniżej 0.3 mm mogą podnieść cenę",
    "Min. szerokość ścieżki, mm",
    "Pilnuj polaryzacji diod i LED (znacznik katody).",
    "Minimalna szerokość ścieżki {0} mm; minimalny otwór po obróbce {1} mm.",
    "LUSTRZANIE",
    "lustrzany",
    "mm",
    "Najdroższe pozycje",
    "otwór montażowy / fiducial",
    "Nazwa",
    "Potrzeba",
    "wymagają uwagi",
    "Wymagają uwagi",
    "Nie",
    "brak odpowiedzi z EasyEDA",
    "brak odpowiedzi z JLCPCB, numer niesprawdzony",
    "Brak uwag.",
    "Nie podano folderu.",
    "brak padów (logo, grafika)",
    "bez numeru",
    "brak zamiennika: żaden dostępny odpowiednik nie ma zgodnego footprintu",
    "Zamienniki nie były potrzebne.",
    "nie zastosowany",
    "Niewyeksportowane do BOM/CPL",
    "nie znaleziono",
    "nie znaleziono wg wartości; atrybut MPN {0} nie użyty: wartość wskazuje inną część",
    "brak w katalogu JLCPCB",
    "nie lustrzanie",
    "Uwagi",
    "Uwagi",
    "Nic.",
    "Przesunięcie, mm",
    "Otwórz folder po zakończeniu",
    "Zamówienie",
    "Kod zamówienia",
    "Zamówienie w JLCPCB",
    "Oryginał",
    "OSP (organiczna powłoka ochronna lutowności)",
    "Pozostałe układy i tranzystory (SOIC, SOT, TSSOP)",
    "Inne wyroby",
    "Pozostałe elementy",
    "Pozostałe SMD: 1206+, diody, LED, kwarce",
    "Grubość miedzi zewnętrznej",
    "Tolerancja obrysu ±{0} mm; wymiary w milimetrach.",
    "Wyjście",
    "Folder wyjściowy",
    "Nałożenie",
    "Obudowa",
    "nie znaleziono folderu pakietu",
    "pady bez pasty (fiducial, zworka, pole kontaktowe)",
    "Format",
    "Papier: kredowy/fotograficzny lub folia transferowa; żelazko 160–180 °C.",
    "część",
    "Część",
    "Nr części",
    "wyprowadzenia części bez padów na płytce: {0}",
    "Numer części",
    "numer wzięty z atrybutu MPN {0}",
    "Części",
    "Koszt części (szacunek)",
    "Wykaz części",
    "części, szacunek",
    "Płytka",
    "Warstwy płytki",
    "Opcje zamówienia płytki",
    "Parametry płytki do formularza zamówienia",
    "Numer części PCB",
    "Liczba płytek",
    "Grubość płytki, mm",
    "Płytka: archiwum",
    "PDF dokumentacji (przez Microsoft Edge)",
    "na płytkę",
    "Na płytkę",
    "faza 2: eksport Fusion",
    "faza 2: dodatek dmxON eksportuje pliki Gerber",
    "pin 1",
    "Klucze pinu 1 i polaryzacji",
    "numery pinów",
    "numery pinów się nie zgadzają",
    "Rozmieszczenie",
    "część biegunowa obrócona o {0}° wg numerów padów 1/2 — biblioteki elementów dwuwyprowadzeniowych numerują pady różnie, sprawdź znacznik polaryzacji w podglądzie",
    "polaryzacji nie da się ustalić z kształtu — sprawdź w podglądzie JLCPCB",
    "Preferuj Basic/Preferred (bez opłaty za podajnik)",
    "Przygotowano w: {0}",
    "Drukuj na drukarce laserowej w skali 100% («Rzeczywisty rozmiar»). Nigdy nie włączaj «Dopasuj do strony».",
    "Płytka drukowana",
    "Wyrób",
    "Pakiet produkcyjny",
    "Raport produkcyjny",
    "fioletowy",
    "Przeznaczenie",
    "Szt.",
    "Powód",
    "czerwony",
    "Ozn. ref.",
    "Nr ref.",
    "Oznaczenie referencyjne",
    "Oznaczenia referencyjne jak na schemacie (GOST 2.710-81); kropka oznacza wyprowadzenie 1 lub katodę.",
    "Oznaczenia referencyjne jak na schemacie (kody literowe wg IEC 81346-2:2019); kropka oznacza wyprowadzenie 1 lub katodę.",
    "Przekaźniki",
    "Usuń",
    "Po lutowaniu usunąć pozostałości topnika, chyba że użyto topnika no-clean.",
    "raport",
    "Raport",
    "zapytanie {0} z {1}",
    "Rezystory",
    "Po instalacji uruchom ponownie Fusion jeden raz.",
    "Uruchom ponownie Fusion, aby usunąć kartę dmxON.",
    "Uruchom ponownie Fusion — karta dmxON pojawi się w edytorach płytki i schematu, a {0} w Automation → Run ULP.",
    "Wynik",
    "Rew.",
    "po prawej",
    "Obrót",
    "korekta obrotu {0} z atrybutu lub pliku zastąpiona obliczoną {1}",
    "Uruchom dmxON FabKit z edytora płytki.",
    "Skala",
    "schemat",
    "Szukaj w katalogu JLCPCB (online)",
    "szukanie zamienników",
    "patrz rysunek",
    "kształt",
    "kształt się zgadza, a numery pinów nie — sprawdź wyprowadzenia",
    "Udział",
    "Wspólne dla wszystkich płytek",
    "arkusz",
    "Arkusz",
    "Arkuszy",
    "Arkusze powstają z tych samych plików Gerber, które trafiają do fabryki: wylewki, odstępy i wycięcia są dokładne. Białe kropki to środki otworów do wiercenia.",
    "Opisy (sitodruk)",
    "Rozmiar",
    "Pomiń oznaczenia",
    "Małe elementy bierne (0201–0805)",
    "zworka lutowana / punkt testowy",
    "Maska lutownicza",
    "Kolor maski",
    "Maska lutownicza: LPI wg IPC-SM-840E, klasa T, {0}, obustronnie; opis farbą nieprzewodzącą, {1}.",
    "Najpierw lutuj stronę z mniejszą liczbą i masą części.",
    "Kolejność lutowania — krok {0} z {1}",
    "Kolejność lutowania i oznaczenia wyprowadzenia 1 wg {0}.",
    "Źródło",
    "Specyfikacja",
    "Etap",
    "Norma",
    "Magazyn",
    "magazyn {0} < potrzeba {1}",
    "w magazynie {0} z {1}",
    "Elementy wrażliwe na wilgoć przechowywać i wygrzewać wg IPC/JEDEC J-STD-033D (MSL wg J-STD-020F).",
    "zamiennik",
    "Zamiennik",
    "ZAMIENNIK",
    "zamienniki",
    "Zamienniki",
    "Zamienniki (odpowiedniki z katalogu JLCPCB)",
    "Wesprzyj projekt",
    "Wykończenie powierzchni",
    "Wykończenie powierzchni: {0}; lutowność wg J-STD-003D.",
    "Przełączniki",
    "Przylutuj jeden pin, wyrównaj do klucza pinu 1, potem lutuj resztę.",
    "Warstw miedzi na płytce: {0} — w domu da się wykonać tylko płytki dwustronne, arkusze obejmują tylko warstwy zewnętrzne (poglądowo lub do uproszczonego prototypu).",
    "na płytce jest wersja {0}, a pakiet ma wersję {1}",
    "na płytce jest wersja {0}, a pakiet ma wersję {1}: popraw napis albo wersję na karcie Tabliczka.",
    "atrybut REV projektu to {0}, a pakiet ma wersję {1}: uruchom FabKit z okna, aby zapisać wersję w projekcie",
    "Dodatek dmxON dołoży tam STEP płytki z elementami i cały folder projektu z chmury (3D, rysunki, pliki).",
    "instalowany jest dodatek dmxON: w edytorach płytki i schematu pojawia się karta <b>dmxON</b> — FabKit, JLC Rules, kopia folderu projektu, aktualizacje z GitHuba",
    "Dodatek dmxON zaktualizowano — uruchom ponownie Fusion, aby działała nowa wersja.",
    "foldery dmxON są dodawane do list ULP, reguł projektowych i CAM w Fusion — <b>{0}</b> jest też w Automation → Run ULP; wbudowane ULP pozostają",
    "Karta dmxON już działa, a {0} jest zaktualizowany — jest też w Automation → Run ULP.",
    "Folder już istnieje i nie został utworzony przez FabKit:",
    "Pakiet trafia do «{0}»: wersję ustawia się na karcie Tabliczka i pojawia się ona w nazwach wszystkich plików i w tabliczkach; poprzedni pakiet tej wersji jest w całości zastępowany.",
    "projekt zostaje skopiowany do <tt>{0}</tt>",
    "Grubość, mm",
    "Elementy przewlekane (THT)",
    "element przewlekany (THT wyłączone)",
    "Elementy przewlekane (THT) — na końcu",
    "THT na końcu, po umyciu SMD; niskie przed wysokimi.",
    "Tabliczka",
    "Pola tabliczki rysunkowej można tu edytować, potem Ctrl+P → Zapisz jako PDF (marginesy: brak).",
    "Tytuł, tytuł uzupełniający",
    "Termotransfer 1:1",
    "Arkusze do termotransferu, skala 1:1",
    "Narzędzie",
    "na górze",
    "Góra",
    "góra / dół",
    "Miedź górna",
    "Pasta górna (szablon)",
    "Arkusze TOP są już lustrzane: po przeniesieniu żelazkiem obraz na płytce czyta się prawidłowo.",
    "Strona górna",
    "Opisy (sitodruk) górne",
    "Maska lutownicza górna",
    "Maska górna (UV): otwarcia czarne",
    "Widok z góry",
    "na górze po lewej",
    "na górze po prawej",
    "Razem",
    "szerokość ścieżek od {0} mm — na granicy możliwości",
    "szerokość ścieżek od {0} mm — standard",
    "szerokość ścieżki {0} mm poniżej minimum {1} mm",
    "Transformatory",
    "Tranzystory",
    "Pinceta i cienki grot; najpierw jedna strona, potem druga.",
    "Typ",
    "Cena jedn.",
    "Używane w raporcie, parametrach zamówienia i widoku płytki.",
    "wartość",
    "Wartość",
    "Sprawdzaj footprinty z JLC; obrót i środek w CPL wg nich",
    "Wersja",
    "Wersja (Rev.)",
    "Wersja {0} zapisana w projekcie (atrybut REV).",
    "wersja {0} — w nazwach plików i tabliczkach{1}",
    "Widok",
    "UWAGA",
    "Co trafia do BOM/CPL",
    "Co utworzyć",
    "Co wgrać",
    "Gdzie",
    "biały",
    "Zapisz numery w atrybutach LCSC_PART",
    "żółty",
    "Tak",
    "Strefa",
    "apertury: {0} · linie: {1} · flashe: {2}",
    "kreski miedzi cieńsze niż 0.05 mm (grafika, logo): {0} — nie zostaną wykonane",
    "plików: {0}, warstw miedzi: {1}",
    "{0} nie ma w katalogu JLCPCB",
    "{0} jest poza obrysem płytki",
    "{0} na {1} V, wymagane {2} V",
    "regiony: {0}",
    "zapytania przez curl: {0}...",
    "narzędzia: {0} · otwory: {1}",
    "{0}, a wartość to {1}",
    "{0}; brak zamiennika wg wartości, pozostawiono {1}"
};

int TR_N = 477;

// fk_docs.ulp — комплект документации по выбранному стандарту (ISO или ГОСТ ЕСКД)
// dmxON FabKit · dmxON by AlexSmith 2026 · см. LICENSE.md
//
// ISO:  перечень документов → чертёж печатной платы → сборочный чертёж → перечень деталей (ISO 7573:2008)
//       → инструкция по монтажу.
// ГОСТ: спецификация (ГОСТ Р 2.106-2019) → сборочный чертёж (СБ) → чертёж платы (ГОСТ 2.417-91)
//       → перечень элементов (ПЭ3, ГОСТ 2.701-2008 / 2.702-2011) → инструкция по монтажу.
// Листы и основные надписи — fk_sheet.ulp. Перечень документов, чертёж платы и нумерацию листов
// дописывает третья фаза (метки <!--FK:DOCLIST-->, <!--FK:FAB-->, {{S:…}}, {{N:…}}).

// ---------------------------------------------------------------- масштаб

real STD_SCALES[] = { 10, 5, 4, 2.5, 2, 1, 0.5, 0.4, 0.25, 0.2, 0.1 };

real pick_scale(real w, real hh, real aw, real ah)
{
    for (int i = 0; i < 11; i++)
        if (w * STD_SCALES[i] <= aw && hh * STD_SCALES[i] <= ah) return STD_SCALES[i];
    return 0.1;
}

string scale_txt(real s)
{
    if (s >= 1) return dnum(s) + ":1";
    return "1:" + dnum(1.0 / s);
}

// формат чертежей: A3, если на A4 плата выходит мельче, чем на A3, и мельче 1:1
void docs_paper()
{
    real W = (bb_x2 - bb_x1) + 6, H = (bb_y2 - bb_y1) + 6;
    real s4 = pick_scale(W, H, 170, 150), s3 = pick_scale(W, H, 380, 150);
    dc_a3 = (s4 < 1 && s3 > s4);
}

// чертёж стороны в масштабе sc (мм на мм) с подписями нужного размера на бумаге
string draw_scaled(int bottom, string sel, int labels, real sc)
{
    real W = (bb_x2 - bb_x1) + 6, H = (bb_y2 - bb_y1) + 6;
    if (ds_crop) { W = ds_vx1 - ds_vx0; H = ds_vy1 - ds_vy0; }
    sprintf(ds_wh, "width:%smm;height:%smm", f3(W * sc), f3(H * sc));
    ds_fsmin = 1.6 / sc;
    ds_fsmax = 2.6 / sc;
    string s = draw_side(bottom, sel, labels, 1000);
    ds_wh = "";
    ds_fsmin = 0.55; ds_fsmax = 2.2;
    return s;
}

// ---------------------------------------------------------------- технические требования / примечания

// пункты через «\n»; ГОСТ 2.316-2008: сквозная нумерация, заголовок не пишут; ISO — заголовок «Примечания»
real nt_cap = 2.5;

real notes_height(string items, real w)
{
    string a[];
    int n = strsplit(a, items, '\n');
    real cpl = w / (nt_cap * 0.62);
    real lines = (doc_std == 1) ? 0 : 1.6;
    for (int i = 0; i < n; i++) {
        if (a[i] == "") continue;
        lines += int((strlen(a[i]) + 4) / cpl) + 1;
    }
    return lines * nt_cap * 1.75 + 2;
}

string notes_html(string items, real w)
{
    string a[];
    int n = strsplit(a, items, '\n');
    string s, st;
    sprintf(st, "width:%smm;font-size:%smm", f3(w), f3(nt_cap / 0.72));
    s = "<div class=\"nt\" style=\"" + st + "\">";
    if (doc_std == 0) s += "<div class=\"nh\">" + h(L("Примечания", "Notes")) + "</div>";
    s += "<ol>";
    for (int i = 0; i < n; i++) if (a[i] != "") s += "<li>" + h(a[i]) + "</li>";
    s += "</ol></div>";
    return s;
}

// примечания (технические требования) к сборочному чертежу
string notes_asm()
{
    string c = istr(dc_class);
    string s = "";
    s += Lf("Монтаж и пайку выполнять по IPC J-STD-001J, класс {0}; приёмка — по IPC-A-610J, класс {0}.",
            "Assemble and solder per IPC J-STD-001J, Class {0}; acceptance per IPC-A-610J, Class {0}.", c, "", "") + "\n";
    if (doc_std == 1)
        s += L("Позиционные обозначения элементов — по схеме электрической принципиальной (ГОСТ 2.710-81); точкой отмечены вывод 1 и катод.",
               "Reference designations as in the circuit diagram (GOST 2.710-81); a dot marks pin 1 or the cathode.") + "\n";
    else
        s += L("Позиционные обозначения — по схеме (буквенные коды IEC 81346-2:2019); точкой отмечены вывод 1 и катод.",
               "Reference designations as in the circuit diagram (letter codes per IEC 81346-2:2019); a dot marks pin 1 or the cathode.") + "\n";
    s += L("Элементы, чувствительные к электростатическому разряду, — с защитой по IEC 61340-5-1:2024.",
           "Handle electrostatic-sensitive devices per IEC 61340-5-1:2024.") + "\n";
    s += L("Элементы, чувствительные к влаге, хранить и сушить по IPC/JEDEC J-STD-033D (уровень MSL — по J-STD-020F).",
           "Store and bake moisture-sensitive devices per IPC/JEDEC J-STD-033D (MSL per J-STD-020F).") + "\n";
    if (doc_std == 1)
        s += Lf("Элементы, не указанные в спецификации {0}, не устанавливать.", "Do not fit parts not listed in {0}.", doc_id("SPEC"), "", "") + "\n";
    else
        s += Lf("Элементы, не указанные в перечне деталей {0}, не устанавливать.", "Do not fit parts not listed in parts list {0}.", doc_id("PL"), "", "") + "\n";
    s += L("После пайки удалить остатки флюса, если применён не безотмывочный флюс.",
           "Remove flux residues after soldering unless a no-clean flux is used.") + "\n";
    s += Lf("Порядок пайки и ключи элементов — по документу {0}.", "Soldering sequence and pin 1 keys per {0}.", doc_id("AI"), "", "") + "\n";
    return s;
}

// ---------------------------------------------------------------- сборочный чертёж

// высота подписей на бумаге, мм: ISO 3098 — не мельче 1,8
real LB_MIN = 1.8, LB_MAX = 2.5;
string ZONE_ISO = "ABCDEFGHJKLMNPQRSTUVWXYZ";
string ZONE_GOST[] = { "А", "Б", "В", "Г", "Д", "Е", "Ж", "И", "К", "Л", "М", "Н", "П", "Р", "С", "Т", "У", "Ф", "Ш", "Э", "Ю", "Я" };

string zone_name(int i)
{
    if (doc_std == 1) return i < 22 ? ZONE_GOST[i] : ZONE_GOST[i % 22] + istr(i / 22 + 1);
    return i < 24 ? strsub(ZONE_ISO, i, 1) : strsub(ZONE_ISO, i % 24, 1) + istr(i / 24 + 1);
}

// лист вида: подпись вида, чертёж в масштабе sc, примечания nts
string asm_sheet(int bottom, string vt, string title, real sc, int labels, string nts, real nw)
{
    string s = sh_open(dc_a3, title, "-");
    real nh = nts != "" ? notes_height(nts, nw) : 0;
    real dw = sh_aw, dh = sh_ah - nh - 8;
    sh_scale = scale_txt(sc);
    string st;
    sprintf(st, "left:0;top:0;width:%smm;height:%smm", f3(dw), f3(dh + 6));
    s += "<div class=\"vw\" style=\"" + st + "\"><div class=\"vl\">" + h(vt) + "</div>" + draw_scaled(bottom, "", labels, sc) + "</div>";
    if (nts != "") s += "<div class=\"nb\">" + notes_html(nts, nw) + "</div>";
    return s + sh_close();
}

void docs_asm()
{
    doc_open("ASM", 1);
    int sides = n_bot > 0 ? 2 : 1;
    real W = (bb_x2 - bb_x1) + 6, H = (bb_y2 - bb_y1) + 6;
    real vx0 = bb_x1 - 3, vy0 = bb_y1 - 3, vx1 = bb_x2 + 3, vy1 = bb_y2 + 3;
    int zones = 0;
    for (int bottom = 0; bottom < sides; bottom++) {
        string vt = bottom ? L("Вид снизу (со стороны пайки)", "Bottom view (solder side)") : L("Вид сверху", "Top view");
        real aw = area_w(dc_a3);
        real nw = aw < 185 ? aw : 185;
        string nts = bottom == 0 ? notes_asm() : "";
        real ah = area_h(dd_sheet == 0, 1) - (nts != "" ? notes_height(nts, nw) : 0) - 8;
        real sc = pick_scale(W, H, aw, ah - 6);
        ds_place = 1;
        int fails = lbl_place(bottom, LB_MIN / sc, LB_MAX / sc, vx0, vy0, vx1, vy1);
        if (fails == 0) {
            printf("%s", asm_sheet(bottom, vt, doc_type("ASM") + " — " + vt, sc, 1, nts, nw));
            ds_place = 0;
            continue;
        }
        // подписи не помещаются: фрагменты в крупном масштабе, на общем виде — их рамки
        real dwd = area_w(dc_a3), dhd = area_h(0, 1) - 14;
        real sd = 0;
        int best = fails;
        for (int i = 10; i >= 0; i--) {
            real s = STD_SCALES[i];
            if (s <= sc || s > 4) continue;
            int f = lbl_place(bottom, LB_MIN / s, LB_MAX / s, vx0, vy0, vx1, vy1);
            if (f < best || sd == 0) { best = f; sd = s; }
            if (f == 0) break;
        }
        int nx = int(ceil(W * sd / dwd)), ny = int(ceil(H * sd / dhd));
        real tw = W / nx, th = H / ny;
        // участки с деталями этой стороны: сверху вниз, слева направо (как на виде)
        real zx1[], zy1[], zx2[], zy2[];
        int nz = 0;
        for (int ty = 0; ty < ny; ty++) {
            for (int tx = 0; tx < nx; tx++) {
                real rx1 = bottom ? vx1 - (tx + 1) * tw : vx0 + tx * tw;
                real ry2 = vy1 - ty * th;
                int any = 0;
                for (int e = 0; e < n_el && !any; e++)
                    if (el_bottom[e] == bottom && el_bx2[e] >= rx1 && el_bx1[e] <= rx1 + tw && el_by2[e] >= ry2 - th && el_by1[e] <= ry2) any = 1;
                if (!any) continue;
                zx1[nz] = rx1; zx2[nz] = rx1 + tw; zy1[nz] = ry2 - th; zy2[nz] = ry2;
                nz++;
            }
        }
        // общий вид: без подписей, с рамками и буквами фрагментов
        n_tl = 0;
        for (int z = 0; z < nz; z++) {
            tl_x1[z] = zx1[z]; tl_y1[z] = zy1[z]; tl_x2[z] = zx2[z]; tl_y2[z] = zy2[z];
            tl_lab[z] = zone_name(zones + z);
            n_tl++;
        }
        printf("%s", asm_sheet(bottom, vt + " · " + Lf("позиционные обозначения — на фрагментах {0}…{1}", "designators on details {0}…{1}",
                                                       zone_name(zones), zone_name(zones + nz - 1), ""),
                               doc_type("ASM") + " — " + vt, sc, 0, nts, nw));
        n_tl = 0;
        // фрагменты: подписи по всей стороне в масштабе sd, у каждого листа — свой участок (с запасом 2 мм)
        lbl_place(bottom, LB_MIN / sd, LB_MAX / sd, vx0, vy0, vx1, vy1);
        for (z = 0; z < nz; z++) {
            ds_crop = 1;
            ds_vx0 = zx1[z] - 2; ds_vx1 = zx2[z] + 2; ds_vy0 = zy1[z] - 2; ds_vy1 = zy2[z] + 2;
            string zt = vt + " · " + L("фрагмент", "detail") + " " + zone_name(zones + z) + " (" + scale_txt(sd) + ")";
            printf("%s", asm_sheet(bottom, zt, doc_type("ASM") + " — " + zt, sd, 1, "", nw));
            ds_crop = 0;
        }
        zones += nz;
        ds_place = 0;
    }
}

// ---------------------------------------------------------------- таблицы текстовых документов

// столбцы: ширины и заголовки через «|», выравнивание ('l'/'c'/'r') — строка символов
string tc_w = "", tc_h = "", tc_al = "";
int tc_n = 0;
real tc_rowmin = 8, tc_head = 15;
real tc_font = 3.47;            // высота шрифта таблицы, мм (перечень ISO подбирает её сам)

// ширина знака для оценки: заглавные и цифры номеров деталей шире среднего
real tc_cw()
{
    return tc_font * 0.62;
}

// самое длинное слово (номер детали, имя) — его нельзя разорвать без потери читаемости
int longest_word(string s)
{
    string w[];
    int n = strsplit(w, s, ' '), m = 0;
    for (int i = 0; i < n; i++) if (strlen(w[i]) > m) m = strlen(w[i]);
    return m;
}

// число строк текста в графе шириной cpl знаков: перенос по словам, длинное слово рвётся (overflow-wrap:anywhere)
int wrap_lines(string s, real cpl)
{
    if (cpl < 1) cpl = 1;
    string w[];
    int n = strsplit(w, s, ' ');
    int lines = 1;
    real cur = 0;
    for (int i = 0; i < n; i++) {
        int L = strlen(w[i]);
        if (L == 0) continue;
        if (L > cpl) {
            if (cur > 0) lines++;
            int extra = int((L - 1) / cpl);
            lines += extra;
            cur = L - extra * cpl;
        }
        else if (cur == 0) cur = L;
        else if (cur + 1 + L <= cpl) cur += 1 + L;
        else { lines++; cur = L; }
    }
    return lines;
}
string tr_cell[];               // строки таблицы: ячейки через табуляцию
int tr_kind[];                  // 0 — строка, 1 — заголовок группы, 2 — пустая
int n_tr = 0;

void tbl_cols(string w, string hdr, string al)
{
    tc_w = w; tc_h = hdr; tc_al = al;
    string a[];
    tc_n = strsplit(a, w, '|');
    n_tr = 0;
    tc_rowmin = doc_std == 1 ? 8 : 6;
    tc_head = doc_std == 1 ? 15 : 10;
    tc_font = 3.47;
}

// ширины граф по содержимому (графы с заданной шириной > 0 не меняются) и самый крупный шрифт,
// при котором самые длинные слова умещаются с запасом; сумма ширин — прежняя (поле рамки)
void tbl_autofit(string fixed)
{
    string ws[], fx[], hs[];
    int n = strsplit(ws, tc_w, '|');
    strsplit(fx, fixed, '|');
    strsplit(hs, tc_h, '|');
    real total = 0, tfix = 0;
    int i, r;
    for (i = 0; i < n; i++) {
        total += strtod(ws[i]);
        if (strtod(fx[i]) > 0) tfix += strtod(fx[i]);
    }
    real fonts[] = { 3.5, 3.0, 2.5, 2.2 };
    real mn[], pf[];
    for (int fi = 0; fi < 4; fi++) {
        tc_font = fonts[fi];
        real cw = tc_cw(), pad = 2.4, smin = 0, gap = 0, spf = 0;
        for (i = 0; i < n; i++) {
            real fw = strtod(fx[i]);
            if (fw > 0) { mn[i] = fw; pf[i] = fw; smin += fw; continue; }
            int tok = longest_word(hs[i]), full = 0;
            for (r = 0; r < n_tr; r++) {
                if (tr_kind[r] == 2) continue;
                string cs[];
                int nc = strsplit(cs, tr_cell[r], '\t');
                if (i >= nc) continue;
                int t = longest_word(cs[i]);
                if (t > tok) tok = t;
                if (tr_kind[r] == 0 && strlen(cs[i]) > full) full = strlen(cs[i]);
            }
            mn[i] = tok * cw + pad;
            if (mn[i] < 8) mn[i] = 8;
            pf[i] = full * cw + pad;
            if (pf[i] < mn[i]) pf[i] = mn[i];
            smin += mn[i]; gap += pf[i] - mn[i]; spf += pf[i];
        }
        // запас 20 % под переносы; самый мелкий шрифт — как получится (длинные слова тогда переносятся)
        if (smin > total * 0.8 && fi < 3) continue;
        real extra = total - smin;
        real take = extra < gap ? extra : gap;
        real left = extra - take;
        string out = "";
        real used = 0;
        int last = -1;
        for (i = 0; i < n; i++) if (strtod(fx[i]) <= 0) last = i;
        for (i = 0; i < n; i++) {
            real w;
            if (strtod(fx[i]) > 0) w = strtod(fx[i]);
            else if (smin > total) w = mn[i] * (total - tfix) / (smin - tfix);
            else w = mn[i] + (gap > 0 ? (pf[i] - mn[i]) * take / gap : 0) + (spf > 0 ? left * pf[i] / spf : 0);
            w = round(w * 10) / 10.0;
            if (i == last) {
                real rest = 0;
                for (int k = i + 1; k < n; k++) rest += strtod(fx[k]) > 0 ? strtod(fx[k]) : 0;
                w = total - used - rest;
            }
            used += w;
            out += (i ? "|" : "") + f3(w);
        }
        tc_w = out;
        return;
    }
}

// строка таблицы; ячейка длиннее 40 строк продолжается в следующих строках (лист её вмещает)
void tbl_row(int kind, string cells)
{
    string ws[];
    strsplit(ws, tc_w, '|');
    while (kind == 0) {
        string cs[];
        int nc = strsplit(cs, cells, '\t'), split = -1;
        for (int i = 0; i < nc && i < tc_n && split < 0; i++) {
            int maxc = int((strtod(ws[i]) - 2.2) / tc_cw() * 40);
            string ci = cs[i];
            if (strlen(ci) <= maxc) continue;
            int cut = maxc;
            while (cut > maxc / 2 && ci[cut] != ',') cut--;
            if (ci[cut] != ',') cut = maxc;
            cs[i] = strsub(ci, 0, cut + 1);
            string row = "", cont = "";
            for (int k = 0; k < nc; k++) {
                row += (k ? "\t" : "") + cs[k];
                cont += (k ? "\t" : "") + (k == i ? trim(strsub(ci, cut + 1)) : "");
            }
            tr_kind[n_tr] = 0; tr_cell[n_tr] = row; n_tr++;
            cells = cont;
            split = i;
        }
        if (split < 0) break;
    }
    tr_kind[n_tr] = kind;
    tr_cell[n_tr] = cells;
    n_tr++;
}

real tbl_rowh(int r)
{
    if (tr_kind[r] != 0) return tc_rowmin;
    string ws[], cs[];
    strsplit(ws, tc_w, '|');
    int nc = strsplit(cs, tr_cell[r], '\t');
    int lines = 1;
    for (int i = 0; i < nc && i < tc_n; i++) {
        real cpl = (strtod(ws[i]) - 2.2) / tc_cw();
        int ln = wrap_lines(cs[i], cpl);
        if (ln > lines) lines = ln;
    }
    real hh = lines * tc_font * 1.27 + 1.8;
    if (hh < tc_rowmin) hh = tc_rowmin;
    return hh;
}

string tbl_head_html()
{
    string ws[], hs[];
    strsplit(ws, tc_w, '|');
    strsplit(hs, tc_h, '|');
    string s, st;
    sprintf(st, "height:%smm", f3(tc_head));
    s = "<tr class=\"th\" style=\"" + st + "\">";
    for (int i = 0; i < tc_n; i++) {
        real w = strtod(ws[i]);
        string cls = (w < 9) ? " class=\"vt\"" : "";
        // слово заголовка шире графы (штатные графы ГОСТ узкие) — мельче шрифт, а не разрыв слова
        string fs = "";
        if (w >= 9) {
            real need = longest_word(hs[i]) * tc_cw() + 2.2;
            if (need > w) {
                real k = w / need;
                if (k < 0.65) k = 0.65;
                sprintf(fs, " style=\"font-size:%s%%\"", f3(k * 100));
            }
        }
        s += "<th" + cls + fs + "><span>" + h(hs[i]) + "</span></th>";
    }
    return s + "</tr>";
}

string tbl_colgroup()
{
    string ws[];
    strsplit(ws, tc_w, '|');
    string s = "<colgroup>";
    for (int i = 0; i < tc_n; i++) s += "<col style=\"width:" + ws[i] + "mm\">";
    return s + "</colgroup>";
}

string tbl_row_html(int r, real hh)
{
    string cs[];
    int nc = strsplit(cs, tr_cell[r], '\t');
    string s, st;
    sprintf(st, "height:%smm", f3(hh));
    string cls = tr_kind[r] == 1 ? " class=\"gr\"" : "";
    s = "<tr" + cls + " style=\"" + st + "\">";
    for (int i = 0; i < tc_n; i++) {
        string v = i < nc ? cs[i] : "";
        char a = tc_al[i];
        string ac = a == 'c' ? "c" : (a == 'r' ? "r" : "l");
        s += "<td class=\"" + ac + "\">" + h(v) + "</td>";
    }
    return s + "</tr>";
}

// вывести таблицу документа по листам (документ уже начат doc_open)
void tbl_print(string title)
{
    int r = 0;
    while (r < n_tr || r == 0) {
        string s = sh_open(0, title, "");
        real avail = sh_ah - tc_head, used = 0;
        string body = "";
        int start = r;
        while (r < n_tr) {
            real hh = tbl_rowh(r);
            if (used + hh > avail && r > start) break;
            // заголовок группы не оставлять внизу листа без строк
            if (tr_kind[r] == 1 && r + 1 < n_tr && used + hh + tbl_rowh(r + 1) > avail && r > start) break;
            body += tbl_row_html(r, hh);
            used += hh;
            r++;
        }
        // пустые строки до конца листа: графы таблицы доводят до основной надписи
        while (used + tc_rowmin <= avail) {
            string st;
            sprintf(st, "height:%smm", f3(tc_rowmin));
            body += "<tr class=\"em\" style=\"" + st + "\">";
            for (int k = 0; k < tc_n; k++) body += "<td></td>";
            body += "</tr>";
            used += tc_rowmin;
        }
        string fs;
        sprintf(fs, "font-size:%smm", f3(tc_font));
        s += "<table class=\"tl\" style=\"" + fs + "\">" + tbl_colgroup() + tbl_head_html() + body + "</table>";
        s += sh_close();
        printf("%s", s);
        if (n_tr == 0) break;
    }
}

// ---------------------------------------------------------------- группы элементов по буквенному коду

string grp_of(string des)
{
    string p = des_prefix(des);
    if (p == "C") return "C";
    if (p == "R" || p == "RN" || p == "RA" || p == "RV" || p == "VR" || p == "RP") return "R";
    if (p == "L" || p == "FB") return "L";
    if (p == "LED" || p == "HL") return "HL";
    if (p == "D" || p == "VD" || p == "CR" || p == "ZD") return "VD";
    if (p == "U" || p == "IC" || p == "DA" || p == "DD") return "DD";
    if (p == "Q" || p == "VT") return "VT";
    if (p == "J" || p == "X" || p == "XS" || p == "XP" || p == "CN" || p == "P" || p == "CON") return "X";
    if (p == "Y" || p == "ZQ" || p == "XTAL" || p == "BQ") return "ZQ";
    if (p == "F" || p == "FU") return "F";
    if (p == "SW" || p == "S" || p == "SA" || p == "SB") return "SA";
    if (p == "K") return "K";
    if (p == "BT" || p == "GB") return "GB";
    if (p == "T" || p == "TR") return "T";
    return "Z";
}

string grp_name(string g)
{
    if (g == "C") return L("Конденсаторы", "Capacitors");
    if (g == "R") return L("Резисторы", "Resistors");
    if (g == "L") return L("Дроссели и индуктивности", "Inductors and ferrite beads");
    if (g == "HL") return L("Светодиоды", "LEDs");
    if (g == "VD") return L("Диоды", "Diodes");
    if (g == "DD") return L("Микросхемы", "Integrated circuits");
    if (g == "VT") return L("Транзисторы", "Transistors");
    if (g == "X") return L("Соединители", "Connectors");
    if (g == "ZQ") return L("Резонаторы", "Crystals and resonators");
    if (g == "F") return L("Предохранители", "Fuses");
    if (g == "SA") return L("Переключатели", "Switches");
    if (g == "K") return L("Реле", "Relays");
    if (g == "GB") return L("Элементы питания", "Batteries");
    if (g == "T") return L("Трансформаторы", "Transformers");
    return L("Прочие элементы", "Other parts");
}

// порядок групп в документах
string GRP_ORDER = "DD|VT|VD|HL|R|C|L|ZQ|F|SA|K|T|GB|X|Z";

// наименование детали строки BOM для спецификации и перечней
string part_title(int g)
{
    string s = g_model[g] != "" ? g_model[g] : g_comment[g];
    // номинал уже содержит номер детали («red NCD0603R3») — без повтора
    if (g_model[g] != "" && g_comment[g] != "" && strstr(strupr(g_comment[g]), strupr(g_model[g])) >= 0) s = g_comment[g];
    else if (g_model[g] != "" && g_comment[g] != "" && strupr(squeeze(g_comment[g])) != strupr(squeeze(g_model[g]))) s += " " + g_comment[g];
    string pk = g_jpkg[g];
    if (g_cpkg[g] != "" && g_cpkg[g] != "-") pk = g_cpkg[g];
    if (pk != "" && strstr(strupr(s), strupr(pk)) < 0) s += (s == "" ? "" : ", ") + pk;
    return s;
}

// номер обозначения — цифры в конце («LED$105» → 105, нет цифр → -1); основа — всё перед ними
int des_tail(string d)
{
    int i = strlen(d);
    while (i > 0 && isdigit(d[i - 1])) i--;
    return i;
}

int des_num(string d)
{
    int i = des_tail(d);
    return i < strlen(d) ? strtol(strsub(d, i)) : -1;
}

string des_stem(string d)
{
    return strsub(d, 0, des_tail(d));
}

// «R1,R2,R3,R5» → «R1…R3, R5» (ГОСТ 2.701: многоточие) или «R1–R3, R5» (ISO); два подряд — через запятую
string des_ranges(string list)
{
    string a[], b[];
    int n = strsplit(a, list, ','), m = 0, i;
    numeric string k[];
    int ix[];
    for (i = 0; i < n; i++) {
        string d = trim(a[i]);
        if (d == "") continue;
        string kk;
        sprintf(kk, "%s%09d", des_stem(d), des_num(d) + 1);
        b[m] = d; k[m] = kk; m++;
    }
    sort(m, ix, k);
    string out = "", dash = doc_std == 1 ? "…" : "–";
    i = 0;
    while (i < m) {
        string d0 = b[ix[i]], st = des_stem(d0);
        int last = des_num(d0), j = i + 1;
        while (j < m && last >= 0 && des_stem(b[ix[j]]) == st && des_num(b[ix[j]]) == last + 1) { last++; j++; }
        string piece = d0;
        if (j - i == 2) piece += ", " + b[ix[i + 1]];
        if (j - i > 2) piece += dash + b[ix[j - 1]];
        out += (out == "" ? "" : ", ") + piece;
        i = j;
    }
    return out;
}

// ключ сортировки обозначения: префикс + номер с ведущими нулями
string des_key(string d)
{
    string p = des_prefix(d);
    string t;
    sprintf(t, "%s%09d", des_stem(d), des_num(d) + 1);
    return t;
}

// ---------------------------------------------------------------- перечень деталей (ISO 7573:2008)

// наименование для перечня: номер детали стоит в своей графе — здесь номинал/описание и корпус
string pl_title(int g)
{
    string m = g_model[g], c = g_comment[g], s = "";
    if (c != "" && strupr(squeeze(c)) != strupr(squeeze(m))) {
        s = c;
        if (m != "") {
            int p = strstr(strupr(s), strupr(m));
            if (p >= 0) s = trim(strsub(s, 0, p) + " " + strsub(s, p + strlen(m)));
        }
    }
    if (s == "") s = m != "" ? m : c;
    string pk = g_jpkg[g];
    if (g_cpkg[g] != "" && g_cpkg[g] != "-") pk = g_cpkg[g];
    if (pk != "" && strstr(strupr(s), strupr(pk)) < 0) s += ", " + pk;
    return s;
}

// изготовитель без приписки в скобках: «UNI-ROYAL(Uniroyal Elec)» -> «UNI-ROYAL»
string brand_short(string b)
{
    int p = strstr(b, "(");
    if (p > 0) {
        int e = strstr(b, ")", p);
        b = trim(strsub(b, 0, p) + (e > p ? " " + strsub(b, e + 1) : ""));
    }
    return b;
}

void docs_pl()
{
    doc_open("PL", 0);
    tbl_cols("10|10|50|40|30|24|16", L("Поз.", "Item") + "|" + L("Кол.", "Qty") + "|" + L("Наименование", "Title") + "|" +
             L("Позиционное обозначение", "Reference designation") + "|" + L("Номер детали", "Part number") + "|" +
             L("Изготовитель", "Manufacturer") + "|" + L("Код заказа", "Order code"), "ccllllll");
    int item = 1;
    tbl_row(0, "1\t1\t" + L("Плата печатная", "Printed circuit board") + "\t—\t" + tb_pcbno + "\t\t");
    string go[];
    int ngo = strsplit(go, GRP_ORDER, '|');
    for (int k = 0; k < ngo; k++) {
        int any = 0;
        for (int g = 0; g < n_g; g++) {
            if (g_merged[g]) continue;
            string d1[];
            strsplit(d1, g_desig[g], ',');
            if (grp_of(d1[0]) != go[k]) continue;
            if (!any) { tbl_row(1, "\t\t" + grp_name(go[k]) + "\t\t\t\t"); any = 1; }
            item++;
            tbl_row(0, istr(item) + "\t" + istr(g_qty[g]) + "\t" + pl_title(g) + "\t" + des_ranges(g_desig[g]) + "\t" +
                       g_model[g] + "\t" + brand_short(g_brand[g]) + "\t" + g_lcsc[g]);
        }
    }
    tbl_autofit("10|10|0|0|0|0|0");
    tbl_print(doc_type("PL"));
}

// ---------------------------------------------------------------- спецификация (ГОСТ Р 2.106-2019, форма 1)

void docs_spec()
{
    doc_open("SPEC", 0);
    tbl_cols("6|6|8|70|63|10|22", L("Формат", "Format") + "|" + L("Зона", "Zone") + "|" + L("Поз.", "Item") + "|" +
             L("Обозначение", "Designation") + "|" + L("Наименование", "Name") + "|" + L("Кол.", "Qty") + "|" +
             L("Примечание", "Note"), "ccclcll");
    string fa = dc_a3 ? "A3" : "A4";
    tbl_row(2, "");
    tbl_row(1, "\t\t\t\t" + L("Документация", "Documentation") + "\t\t");
    tbl_row(2, "");
    tbl_row(0, fa + "\t\t\t" + doc_id("ASM") + "\t" + L("Сборочный чертёж", "Assembly drawing") + "\t\t");
    // ГОСТ Р 2.106: формат не из основного ряда — «*» в графе «Формат», сам формат — в примечании
    int sch_basic = strstr(sch_fmt_txt, "×") < 0 && strstr(sch_fmt_txt, ",") < 0;    // A0…A4
    if (dc_sch && sch_fmt_txt != "") tbl_row(0, (sch_basic ? sch_fmt_txt : "*") + "\t\t\t" + doc_id("SCH") + "\t" + L("Схема электрическая принципиальная", "Circuit diagram") + "\t\t" + (sch_basic ? "" : "*" + sch_fmt_txt));
    tbl_row(0, "A4\t\t\t" + doc_id("PE") + "\t" + L("Перечень элементов", "List of elements") + "\t\t");
    tbl_row(2, "");
    tbl_row(1, "\t\t\t\t" + L("Детали", "Parts") + "\t\t");
    tbl_row(2, "");
    tbl_row(0, fa + "\t\t1\t" + tb_pcbno + "\t" + L("Плата печатная", "Printed circuit board") + "\t1\t");
    tbl_row(2, "");
    tbl_row(1, "\t\t\t\t" + L("Прочие изделия", "Other items") + "\t\t");
    int pos = 1;
    string go[];
    int ngo = strsplit(go, GRP_ORDER, '|');
    for (int k = 0; k < ngo; k++) {
        int any = 0;
        for (int g = 0; g < n_g; g++) {
            if (g_merged[g]) continue;
            string d1[];
            strsplit(d1, g_desig[g], ',');
            if (grp_of(d1[0]) != go[k]) continue;
            if (!any) { tbl_row(2, ""); tbl_row(1, "\t\t\t\t" + grp_name(go[k]) + "\t\t"); any = 1; }
            pos++;
            string nm = part_title(g);
            if (g_brand[g] != "") nm += " " + brand_short(g_brand[g]);
            tbl_row(0, "\t\t" + istr(pos) + "\t\t" + nm + "\t" + istr(g_qty[g]) + "\t" + des_ranges(g_desig[g]));
        }
    }
    tbl_print(L("Спецификация", "Specification"));
}

// ---------------------------------------------------------------- перечень элементов (ГОСТ 2.701-2008, 2.702-2011)

void docs_pe()
{
    doc_open("PE", 0);
    tbl_cols("20|110|10|45", L("Поз. обозначение", "Ref. designation") + "|" + L("Наименование", "Name") + "|" + L("Кол.", "Qty") + "|" +
             L("Примечание", "Note"), "clcl");
    // элементы по порядку обозначений
    numeric string ek[];
    int ei[], n = 0, e;
    for (e = 0; e < n_el; e++) { ek[n] = des_key(el_name[e]); n++; }
    sort(n, ei, ek);
    string go[];
    int ngo = strsplit(go, GRP_ORDER, '|');
    for (int k = 0; k < ngo; k++) {
        int any = 0;
        int i = 0;
        while (i < n) {
            e = ei[i];
            if (grp_of(el_name[e]) != go[k]) { i++; continue; }
            if (!any) { tbl_row(2, ""); tbl_row(1, "\t" + grp_name(go[k]) + "\t\t"); any = 1; }
            // подряд идущие одинаковые элементы — одной строкой «R1…R5»
            int g = el_group[e];
            string nm = g >= 0 ? part_title(g) : el_value[e];
            int j = i + 1, cnt = 1;
            string last = el_name[e];
            while (j < n) {
                int e2 = ei[j];
                if (grp_of(el_name[e2]) != go[k]) break;
                int g2 = el_group[e2];
                string nm2 = g2 >= 0 ? part_title(g2) : el_value[e2];
                if (nm2 != nm || des_stem(el_name[e2]) != des_stem(el_name[e])) break;
                if (des_num(last) < 0 || des_num(el_name[e2]) != des_num(last) + 1) break;
                last = el_name[e2];
                cnt++; j++;
            }
            string ref = el_name[e];
            if (cnt == 2) ref += ", " + last;
            if (cnt > 2) ref += "…" + last;
            string note = "";
            if (g >= 0 && g_brand[g] != "") note = brand_short(g_brand[g]);
            tbl_row(0, ref + "\t" + nm + "\t" + istr(cnt) + "\t" + note);
            i = j;
        }
    }
    tbl_print(L("Перечень элементов", "List of elements"));
}

// ---------------------------------------------------------------- инструкция по монтажу: порядок пайки и ключи

void docs_steps()
{
    int s, e, i, k;
    int n_steps = 0, stepno = 0;
    for (s = 1; s <= STEP_N; s++) {
        int has = 0;
        for (e = 0; e < n_el; e++) if (el_step[e] == s) has = 1;
        n_steps += has;
    }
    real W = (bb_x2 - bb_x1) + 6, H = (bb_y2 - bb_y1) + 6;
    for (s = 1; s <= STEP_N; s++) {
        int n = 0, any_bot = 0, any_top = 0;
        for (e = 0; e < n_el; e++) {
            if (el_step[e] != s) continue;
            n++;
            if (el_bottom[e]) any_bot = 1; else any_top = 1;
        }
        if (n == 0) continue;
        stepno++;
        int bottom = (any_bot && !any_top);
        numeric string gk[];
        string gdes[], gval[], gpkg[], gkey[], gkl[];
        int gdiff[], gnk[];
        int gq[], ng = 0;
        for (e = 0; e < n_el; e++) {
            if (el_step[e] != s) continue;
            string key = el_comment[e] + "|" + el_jpkg[e];
            int f = -1;
            for (k = 0; k < ng; k++) if (gk[k] == key) { f = k; break; }
            if (f < 0) {
                f = ng++;
                gk[f] = key; gdes[f] = ""; gval[f] = el_comment[e]; gpkg[f] = el_jpkg[e]; gq[f] = 0; gkey[f] = ""; gkl[f] = ""; gdiff[f] = 0; gnk[f] = 0;
            }
            if (gdes[f] != "") gdes[f] += ", ";
            gdes[f] += el_name[e];
            gq[f]++;
            if (needs_key(e) && el_has_p1[e]) {
                string kr = "1 " + key_arrow(e);
                if (el_p1cat[e]) kr = "K " + key_arrow(e);
                if (gq[f] == 1) gkey[f] = kr;
                else if (gkey[f] != kr) gdiff[f] = 1;
                if (gkl[f] != "") gkl[f] += ", ";
                gkl[f] += el_name[e] + " " + kr;
                gnk[f]++;
            }
        }
        for (k = 0; k < ng; k++) {
            if (!gdiff[k]) continue;
            if (gnk[k] <= 8) gkey[k] = gkl[k];
            else gkey[k] = L("см. чертёж", "see drawing");
        }
        int ord[];
        sort(ng, ord, gk);
        // A4 — чертёж сверху, таблица снизу в две колонки; A3 — чертёж слева, таблица справа
        int stack = !dc_a3;
        int from = 0, prt = 0;
        while (from < ng) {
            string tt = Lf("Порядок пайки — шаг {0} из {1}", "Soldering order — step {0} of {1}", istr(stepno), istr(n_steps), "");
            string pg = sh_open(dc_a3, tt, "-");
            real tip_h = 15;
            real dw, dh, tw, th;
            if (stack) { dw = sh_aw; dh = (sh_ah - tip_h - 8) * 0.55; tw = sh_aw; th = sh_ah - tip_h - 8 - dh - 4; }
            else { dw = sh_aw * 0.56; dh = sh_ah - tip_h - 8; tw = sh_aw - dw - 4; th = sh_ah - tip_h - 8; }
            int ncol = stack ? 2 : 1;
            real colw = (tw - (ncol - 1) * 3) / ncol;
            int budget = int((th - 7) / 4.3);
            if (budget < 3) budget = 3;
            int wrap = int((colw * 0.42) / 1.55), wv = int((colw * 0.2) / 1.55), wk = int((colw * 0.18) / 1.55);
            if (wrap < 8) wrap = 8;
            if (wv < 6) wv = 6;
            if (wk < 6) wk = 6;
            int rl[];
            for (i = 0; i < ng; i++) {
                k = ord[i];
                int a1 = 1 + strlen(des_ranges(gdes[k])) / wrap, a2 = 1 + strlen(gval[k]) / wv, a3 = 1;
                if (gkey[k] != "") a3 = 1 + strlen(gkey[k]) / wk;
                rl[i] = max(a1, max(a2, a3));
            }
            int cut[];
            int to = from, c, cap = budget;
            int rest = 0;
            for (i = from; i < ng; i++) rest += rl[i];
            if (rest <= budget * ncol) cap = (rest + ncol - 1) / ncol;
            for (c = 0; c < ncol; c++) {
                int lines = 0, c0 = to;
                while (to < ng) {
                    if (lines + rl[to] > cap && to > c0) break;
                    lines += rl[to];
                    to++;
                }
                cut[c] = to;
            }
            prt++;
            string sel = "|";
            for (i = from; i < to; i++) {
                string a[];
                int na = strsplit(a, replace_all(gdes[ord[i]], " ", ""), ',');
                for (k = 0; k < na; k++) sel += a[k] + "|";
            }
            real sc = pick_scale(W, H, dw, dh - 6);
            sh_scale = scale_txt(sc);
            string st;
            string cap_txt = tt;
            if (prt > 1 || to < ng) cap_txt += " · " + L("часть", "part") + " " + istr(prt);
            sprintf(st, "left:0;top:0;width:%smm;height:%smm", f3(dw), f3(dh));
            pg += "<div class=\"vw\" style=\"" + st + "\"><div class=\"vl\">" + h(cap_txt) + "</div>" + draw_scaled(bottom, sel, 0, sc) + "</div>";
            if (stack) sprintf(st, "left:0;top:%smm;width:%smm", f3(dh + 4), f3(tw));
            else sprintf(st, "left:%smm;top:0;width:%smm", f3(dw + 4), f3(tw));
            pg += "<div class=\"sg\" style=\"" + st + ";grid-template-columns:repeat(" + istr(ncol) + ",1fr)\">";
            int c_from = from;
            for (c = 0; c < ncol; c++) {
                if (cut[c] <= c_from) break;
                pg += "<table class=\"ts\"><tr><th>" + h(L("Шт", "Qty")) + "</th><th>" + h(L("Обозначения", "Designators")) + "</th><th>" +
                      h(L("Номинал", "Value")) + "</th><th>" + h(L("Корпус", "Package")) + "</th><th>" + h(L("Ключ", "Key")) + "</th></tr>";
                for (i = c_from; i < cut[c]; i++) {
                    k = ord[i];
                    pg += "<tr><td class=\"r\">" + istr(gq[k]) + "</td><td>" + h(des_ranges(gdes[k])) + "</td><td>" + h(gval[k]) + "</td><td>" + h(gpkg[k]) +
                          "</td><td>" + h(gkey[k]) + "</td></tr>";
                }
                pg += "</table>";
                c_from = cut[c];
            }
            pg += "</div>";
            sprintf(st, "left:0;bottom:0;width:%smm;height:%smm", f3(sh_aw), f3(tip_h));
            pg += "<div class=\"tip\" style=\"" + st + "\"><b>" + h(step_txt(s)) + "</b><br>" + h(step_tip(s)) + "<br>" +
                  h(L("Ключ: 1 — вывод 1, K — катод, стрелка — где он от центра корпуса.",
                      "Key: 1 — pin 1, K — cathode, the arrow shows where it is from the body centre.")) + "</div>";
            pg += sh_close();
            printf("%s", pg);
            from = to;
        }
    }
}

// миниатюра элемента (ключ)
string el_thumb(int e)
{
    real mg = max(el_bx2[e] - el_bx1[e], el_by2[e] - el_by1[e]) * 0.12 + 0.3;
    real x0 = el_bx1[e] - mg, x1 = el_bx2[e] + mg, y0 = el_by1[e] - mg, y1 = el_by2[e] + mg;
    real W = x1 - x0, H = y1 - y0;
    string s, tr;
    if (el_bottom[e]) sprintf(tr, "matrix(-1 0 0 -1 %s %s)", f3(x1), f3(y1));
    else sprintf(tr, "matrix(1 0 0 -1 %s %s)", f3(-x0), f3(y1));
    sprintf(s, "<svg class=\"brd\" viewBox=\"0 0 %s %s\" preserveAspectRatio=\"xMidYMid meet\" xmlns=\"http://www.w3.org/2000/svg\"><g transform=\"%s\">",
            f3(W), f3(H), tr);
    s += "<g class=\"e1\"><g class=\"pd\">" + el_pads[e] + "</g>";
    if (el_gfx[e] != "") s += "<path class=\"gx\" d=\"" + el_gfx[e] + "\"/>";
    s += el_circ[e] + "</g>";
    if (el_has_p1[e]) {
        string t;
        real r = max(W, H) * 0.05;
        sprintf(t, "<circle class=\"k1\" cx=\"%s\" cy=\"%s\" r=\"%s\"/>", f3(el_p1x[e]), f3(el_p1y[e]), f3(r));
        s += t;
    }
    s += "</g></svg>";
    return s;
}

void docs_keys()
{
    int e, n = 0, i;
    int list[];
    numeric string kk[];
    int ord[];
    for (e = 0; e < n_el; e++) {
        if (!needs_key(e) || !el_has_p1[e]) continue;
        kk[n] = des_key(el_name[e]);
        list[n] = e;
        n++;
    }
    if (n == 0) return;
    sort(n, ord, kk);
    int cols = dc_a3 ? 8 : 4, rows = 5;
    int per = cols * rows;
    for (int from = 0; from < n; from += per) {
        string tt = L("Ключи и полярность", "Pin 1 and polarity keys");
        string pg = sh_open(dc_a3, tt, "");
        string st;
        sprintf(st, "grid-template-columns:repeat(%d,1fr);grid-auto-rows:%smm", cols, f3((sh_ah - 8) / rows - 2.5));
        pg += "<div class=\"vl\">" + h(tt) + "</div><div class=\"keys\" style=\"" + st + "\">";
        for (i = from; i < from + per && i < n; i++) {
            e = list[ord[i]];
            string mk = L("вывод 1", "pin 1");
            if (el_p1cat[e]) mk = L("катод", "cathode");
            string side = "";
            if (el_bottom[e]) side = " · " + h(L("снизу", "bottom"));
            string pn = el_comment[e];
            int g = el_group[e];
            if (g >= 0 && g_model[g] != "") pn = g_model[g];
            pg += "<div class=\"key\"><div class=\"d\">" + h(el_name[e]) + side + "</div>" + el_thumb(e) + "<div class=\"s\">" +
                  h(pn + " · " + el_jpkg[e]) + "<br>" + h(mk) + ": " + h(key_where(e)) + "</div></div>";
        }
        pg += "</div>";
        pg += sh_close();
        printf("%s", pg);
    }
}

// ---------------------------------------------------------------- оформление содержимого листов

string DC_CSS =
    "svg *{vector-effect:non-scaling-stroke}" +
    ".vw{position:absolute;display:flex;flex-direction:column;align-items:center;justify-content:center}" +
    ".vl{font-size:3.5mm;margin:0 0 1.5mm;text-align:center;width:100%}" +
    ".brd .ol{fill:#fff;stroke:#000;stroke-width:1.1px}.brd .olc{fill:#fff;stroke:#000;stroke-width:.8px}" +
    ".brd .pd rect,.brd .pd circle{fill:#c4c4c4;stroke:none}.brd .pd0 rect,.brd .pd0 circle{fill:#e8e8e8;stroke:none}" +
    ".brd .gx{fill:none;stroke:#222;stroke-width:.7px}" +
    ".brd .e0{opacity:.35}.brd .e1 .pd rect,.brd .e1 .pd circle{fill:#d0472c}.brd .e1 .gx{stroke:#8f2a1a;stroke-width:1.2px}" +
    ".brd .k1{fill:#000;stroke:#fff;stroke-width:.5px}" +
    ".brd text{font-family:Arial,sans-serif;font-style:normal;text-anchor:middle;fill:#000;paint-order:stroke;stroke:#fff;stroke-width:1.6px;stroke-linejoin:round;font-weight:600}" +
    ".brd text.lb0{fill:#9a9a9a;font-weight:400}.brd text.lb1{fill:#8f2a1a}" +
    ".brd text.la{font-weight:400;stroke-width:1.2px}" +
    ".brd .tf{fill:none;stroke:#1d5fa8;stroke-width:1.2px;stroke-dasharray:7 4}.brd text.tl{fill:#1d5fa8;font-weight:700}" +
    // технические требования / примечания: над основной надписью, справа
    ".nb{position:absolute;right:0;bottom:0}.nt{line-height:1.25}.nt .nh{font-weight:700;margin-bottom:1mm}" +
    ".nt ol{margin:0;padding-left:5mm}.nt li{margin:0 0 .6mm}" +
    // таблицы текстовых документов
    "table.tl{border-collapse:collapse;table-layout:fixed;width:100%;font-size:3.47mm}" +
    "table.tl th,table.tl td{border:.25mm solid #000;padding:0 1mm;vertical-align:middle;overflow:hidden;line-height:1.25;overflow-wrap:anywhere;word-break:break-word}" +
    ".gost table.tl th,.gost table.tl td{border-left-width:.6mm;border-right-width:.6mm}.gost table.tl tr.th th{border-width:.6mm}" +
    "table.tl th{font-weight:400;text-align:center}table.tl th.vt span{display:inline-block;writing-mode:vertical-rl;transform:rotate(180deg);white-space:nowrap}" +
    "table.tl td.c{text-align:center}table.tl td.r{text-align:right}table.tl tr.gr td{text-align:center;text-decoration:underline}" +
    // порядок пайки
    ".sg{position:absolute;display:grid;gap:3mm;align-items:start}" +
    "table.ts{border-collapse:collapse;width:100%;font-size:2.9mm}table.ts th,table.ts td{border:.2mm solid #555;padding:.3mm 1mm;text-align:left;vertical-align:top}" +
    "table.ts th{background:#efefea;font-weight:600}table.ts td.r{text-align:right}" +
    ".tip{position:absolute;border-top:.25mm solid #000;padding-top:1.2mm;font-size:2.9mm;line-height:1.25}" +
    // ключи
    ".keys{display:grid;gap:2.5mm}" +
    ".key{border:.2mm solid #999;border-radius:1.5mm;padding:1.2mm;display:flex;flex-direction:column;overflow:hidden}" +
    ".key svg{flex:1;width:100%;min-height:0}.key .d{font-size:3mm;font-weight:700}.key .s{font-size:2.3mm;line-height:1.15}" +
    // перечень документов (ISO)
    ".dl h2{font-size:7mm;margin:2mm 0 1mm;line-height:1.1}.dl .sub{font-size:3.5mm;margin-bottom:4mm}" +
    ".dl .rnd{position:relative;background:#14181d;border-radius:2mm;padding:3mm;margin:0 auto 4mm}.dl .rnd img{display:block;width:100%}" +
    ".dl table{border-collapse:collapse;width:100%;font-size:3.2mm;margin-bottom:4mm}.dl th,.dl td{border:.25mm solid #000;padding:.8mm 1.2mm;text-align:left}" +
    ".dl th{font-weight:400;background:#f1f1ee}" +
    // чертёж платы: таблицы
    ".fx table{border-collapse:collapse;font-size:2.9mm}.fx th,.fx td{border:.25mm solid #000;padding:.4mm 1.2mm;text-align:left}.fx th{font-weight:400;background:#f1f1ee}" +
    ".fx td.n{text-align:right}.lgrid{display:grid;gap:3mm}.lcell{border:.2mm solid #999}.lcell .im{background:#14181d;padding:1.5mm}" +
    ".lcell .im img{display:block;width:100%;height:auto}.lcell .tx2{padding:1mm 1.5mm;font-size:2.8mm}";

// синхронизация полей штампа между листами (необязательная надстройка)
string DC_JS =
    "document.addEventListener('input',function(e){var t=e.target,f=t&&t.getAttribute&&t.getAttribute('data-f');if(!f)return;" +
    "var a=document.querySelectorAll('[data-f=\"'+f+'\"]');for(var i=0;i<a.length;i++)if(a[i]!==t)a[i].textContent=t.textContent;});";

// ---------------------------------------------------------------- весь документ первой фазы

void docs_phase1(string path, string base, int n_layers, string stamp)
{
    int e;
    for (e = 0; e < n_el; e++) el_step[e] = calc_step(e);
    docs_paper();
    output(path, "wt") {
        printf("<!DOCTYPE html>\n<html lang=\"%s\">\n<head>\n<meta charset=\"utf-8\">\n", LANG_CODE[ui_lang]);
        printf("<meta name=\"generator\" content=\"%s\">\n", h(fk_title()));
        printf("<title>%s</title>\n<style>%s%s</style>\n</head>\n<body>\n", h(base + " · " + L("Документация", "Documentation")), SH_CSS, DC_CSS);
        printf("<div class=\"bar\">%s</div>\n",
               h(L("Поля основной надписи можно править прямо здесь, затем Ctrl+P → Сохранить как PDF (поля: нет).",
                   "Title block fields are editable here, then Ctrl+P → Save as PDF (margins: none).")));
        if (doc_std == 1) {
            // форматы листов схемы нужны спецификации раньше самой схемы
            if (dc_sch) sc_collect();
            if (dc_sch && sc_n > 0) sch_fmt_txt = sch_formats();
            docs_spec();
            docs_asm();
            printf("<!--FK:FAB-->\n");
            if (dc_sch) docs_sch();
            docs_pe();
        } else {
            printf("<!--FK:DOCLIST-->\n");
            printf("<!--FK:FAB-->\n");
            docs_asm();
            docs_pl();
            if (dc_sch) docs_sch();
        }
        doc_open("AI", 1);
        docs_steps();
        docs_keys();
        printf("<script>%s</script>\n</body>\n</html>\n", DC_JS);
    }
}

#usage "en: <b>Install dmxON FabKit into Autodesk Fusion</b><p>"
       "Copies the project to Documents\\dmxON and installs the dmxON add-in: the dmxON tab "
       "(FabKit, JLC Rules, backup, updates) appears in the PCB and schematic editors, "
       "and dmxON_FabKit appears in Automation → Run ULP.<p>"
       "<author>dmxON by AlexSmith 2026</author>",
       "ru: <b>Установка dmxON FabKit во Fusion</b><p>"
       "Копирует проект в Документы\\dmxON и ставит надстройку dmxON: в редакторах платы и схемы "
       "появляется вкладка dmxON (FabKit, JLC Rules, бэкап, обновления), "
       "а dmxON_FabKit — в Automation → Run ULP.<p>"
       "<author>dmxON by AlexSmith 2026</author>",
       "es: <b>Instalar dmxON FabKit en Autodesk Fusion</b><p>"
       "Copia el proyecto en Documentos\\dmxON e instala el complemento dmxON: la pestaña dmxON "
       "(FabKit, JLC Rules, copia de seguridad, actualizaciones) aparece en los editores de placa y esquema, "
       "y dmxON_FabKit en Automation → Run ULP.<p>"
       "<author>dmxON by AlexSmith 2026</author>",
       "de: <b>dmxON FabKit in Autodesk Fusion installieren</b><p>"
       "Kopiert das Projekt nach Dokumente\\dmxON und installiert das dmxON-Add-in: Der Reiter dmxON "
       "(FabKit, JLC Rules, Sicherung, Updates) erscheint im Platinen- und Schaltplan-Editor, "
       "dmxON_FabKit unter Automation → Run ULP.<p>"
       "<author>dmxON by AlexSmith 2026</author>",
       "pl: <b>Instalacja dmxON FabKit w Autodesk Fusion</b><p>"
       "Kopiuje projekt do Dokumenty\\dmxON i instaluje dodatek dmxON: w edytorach płytki i schematu "
       "pojawia się karta dmxON (FabKit, JLC Rules, kopia zapasowa, aktualizacje), "
       "a dmxON_FabKit w Automation → Run ULP.<p>"
       "<author>dmxON by AlexSmith 2026</author>"

// Установщик dmxON FabKit · dmxON by AlexSmith 2026 · см. LICENSE.md
//
// Fusion хранит папки ULP / правил / CAM в своих настройках (Preferences → Electronics → Directory),
// доступ к которым есть только у надстроек на Python. Поэтому установщик кладёт проект в Документы/dmxON
// и ставит надстройку dmxON (fusion-addin/dmxON) в папку надстроек Fusion; она добавляет папки сама —
// при запуске Fusion и сразу по запросу из .inbox, если уже работает.

#include "lib/fk_strings.ulp"
#include "lib/fk_lang.ulp"
#include "lib/fk_core.ulp"
#include "lib/fk_addin.ulp"

string IN_NAME   = "dmxON FabKit";
string IN_DIR    = "dmxON-FabKit";
string IN_MAIN   = "dmxON_FabKit";
string OTHER_DIR = "dmxON-JLC-Rules/dmxON_JLC_Setup.ulp";   // второй инструмент dmxON

string in_dir(string p)
{
    p = replace_all(p, "\\", "/");
    while (ends_with(p, "/")) p = strsub(p, 0, strlen(p) - 1);
    return p;
}

// список папок «a;b;c» без путей внутри base (без учёта регистра)
string in_without(string list, string base)
{
    string a[];
    int n = strsplit(a, list, ';');
    string t = "";
    base = strlwr(in_dir(base));
    for (int i = 0; i < n; i++) {
        string p = strlwr(in_dir(a[i]));
        if (a[i] == "" || p == base || strstr(p, base + "/") == 0) continue;
        t += (t == "" ? "" : ";") + a[i];
    }
    return t;
}

// установщик 2.1.0 писал папки в EAGLE:Directories.* — Fusion их не читает; вернуть как было
string LEGACY_KEYS[] = { "Ulp", "Dru", "Cam" };

void legacy_cleanup()
{
    string was = cfgget("dmxon.install.usedefault", "");
    if (was == "" && cfgget("dmxon.install.fabkit.dst", "") == "" && cfgget("dmxon.install.jlc.dst", "") == "") return;
    for (int k = 0; k < 3; k++) {
        string key = "EAGLE:Directories." + LEGACY_KEYS[k];
        cfgset(key, in_without(cfgget(key, ""), dmx_base()));
    }
    if (was != "") cfgset("EAGLE:Directories.UseDefault", was);
    cfgset("dmxon.install.usedefault", "");
    cfgset("dmxon.install.fabkit.dst", "");
    cfgset("dmxon.install.jlc.dst", "");
}

lang_load();
string src = in_dir(filedir(argv[0]));
string home = local_home();
if (home == "") {
    dlgMessageBox(L("Не удалось определить папку пользователя.", "Cannot find the user folder."), "OK");
    exit(EXIT_FAILURE);
}
runner_init(home + "/AppData/Local/Temp");
string dst = dmx_base() + "/" + IN_DIR;
string adst = addin_dir();
string asrc = src + "/fusion-addin/dmxON";
int installed = file_exists(dst + "/" + IN_MAIN + ".ulp");
int alive = addin_alive();

int action = 0;
int sel_lang = ui_lang;
while (1) {
    sel_lang = ui_lang;
    string txt = "<h3>" + IN_NAME + " " + FK_VERSION + "</h3>" +
        "<p>" + L("Установка в Autodesk Fusion:", "Installation into Autodesk Fusion:") + "</p><ul>" +
        "<li>" + Lf("проект копируется в <tt>{0}</tt>", "the project is copied to <tt>{0}</tt>", dst, "", "") + "</li>" +
        "<li>" + L("ставится надстройка dmxON: в редакторах платы и схемы появляется вкладка <b>dmxON</b> — FabKit, JLC Rules, бэкап папки проекта, обновления с GitHub",
                   "the dmxON add-in is installed: the <b>dmxON</b> tab appears in the PCB and schematic editors — FabKit, JLC Rules, backup of the design folder, updates from GitHub") + "</li>" +
        "<li>" + Lf("папки dmxON добавляются в списки ULP, правил и CAM Fusion — <b>{0}</b> есть и в Automation → Run ULP; встроенные ULP остаются",
                    "the dmxON folders are added to Fusion's ULP, design rules and CAM lists — <b>{0}</b> is also in Automation → Run ULP; the built-in ULPs stay", IN_MAIN, "", "") + "</li></ul>" +
        (alive ? "" : "<p><b>" + L("После установки один раз перезапустите Fusion.", "Restart Fusion once after installing.") + "</b></p>") +
        (installed ? "<p>" + L("Уже установлено — «Установить» обновит файлы.", "Already installed — «Install» updates the files.") + "</p>" : "");
    action = dlgDialog(L("Установка", "Installation") + " · " + IN_NAME) {
        dlgHBoxLayout {
            dlgStretch(1);
            dlgLabel(L("Язык", "Language"));
            dlgComboBox(LANG_NAME, sel_lang) { if (sel_lang != ui_lang) { ui_lang = sel_lang; lang_save(); dlgAccept(9); } }
        }
        dlgHBoxLayout {
            dlgVBoxLayout dlgSpacing(240);
            dlgVBoxLayout {
                dlgHBoxLayout dlgSpacing(580);
                dlgTextView(txt);
            }
        }
        dlgHBoxLayout {
            dlgPushButton("+" + L("Установить", "Install")) dlgAccept(1);
            if (installed) dlgPushButton(L("Удалить", "Remove")) dlgAccept(2);
            dlgStretch(1);
            dlgPushButton("-" + L("Отмена", "Cancel")) dlgReject();
        }
    };
    if (action == 9) continue;
    break;
}
if (action <= 0) exit(0);
legacy_cleanup();

// ---- удалить: папку инструмента; надстройку — вместе с последним инструментом dmxON
if (action == 2) {
    shell("rmdir /s /q " + qp(dst));
    int last = !file_exists(dmx_base() + "/" + OTHER_DIR);
    addin_request("register", "");
    if (last) shell("rmdir /s /q " + qp(adst));
    dlgMessageBox(L("dmxON FabKit удалён.", "dmxON FabKit removed.") +
                  (last ? "\n" + L("Перезапустите Fusion, чтобы убрать вкладку dmxON.", "Restart Fusion to remove the dmxON tab.") : ""), "OK");
    exit(0);
}

// ---- установить
if (strlwr(src) != strlwr(dst)) {
    // robocopy: коды 0–7 — успех; .git и сам установщик не копируются
    shell("mkdir " + qp(dst) + " 2>nul");
    shell("robocopy " + qp(src) + " " + qp(dst) + " /E /NFL /NDL /NJH /NJS /NP /XD .git .github __pycache__ /XF INSTALL.ulp >nul");
}
if (!file_exists(dst + "/" + IN_MAIN + ".ulp")) {
    dlgMessageBox(L("Не удалось скопировать файлы в:", "Cannot copy the files to:") + "\n" + dst, "OK");
    exit(EXIT_FAILURE);
}
// надстройка: ставится, если её нет или в пакете новее
string av = addin_version(asrc), ai = addin_version(adst);
int addin_new = 0;
if (av != "" && (ai == "" || version_cmp(av, ai) > 0)) {
    shell("mkdir " + qp(adst) + " 2>nul");
    shell("robocopy " + qp(asrc) + " " + qp(adst) + " /E /NFL /NDL /NJH /NJS /NP /XD __pycache__ >nul");
    addin_new = addin_version(adst) == av;
}
if (addin_version(adst) == "") {
    dlgMessageBox(L("Не удалось установить надстройку dmxON в:", "Cannot install the dmxON add-in to:") + "\n" + adst, "OK");
    exit(EXIT_FAILURE);
}
addin_request("register", "");

string msg = L("Готово.", "Done.") + "\n\n";
if (alive && !addin_new)
    msg += Lf("Вкладка dmxON уже работает, {0} обновлён — он есть и в Automation → Run ULP.",
              "The dmxON tab is already running and {0} is updated — it is also in Automation → Run ULP.", IN_NAME, "", "");
else if (alive)
    msg += L("Надстройка dmxON обновлена — перезапустите Fusion, чтобы она заработала в новой версии.",
             "The dmxON add-in is updated — restart Fusion to run the new version.");
else
    msg += Lf("Перезапустите Fusion — в редакторах платы и схемы появится вкладка dmxON, а {0} — в Automation → Run ULP.",
              "Restart Fusion — the dmxON tab appears in the PCB and schematic editors, and {0} in Automation → Run ULP.", IN_MAIN, "", "");
dlgMessageBox(msg + "\n\n" + dst, "OK");
